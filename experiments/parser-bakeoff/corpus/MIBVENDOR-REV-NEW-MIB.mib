-- SPDX-License-Identifier: CC0-1.0
MIBVENDOR-REV-NEW-MIB DEFINITIONS ::= BEGIN

IMPORTS
    MODULE-IDENTITY, OBJECT-TYPE, Integer32, enterprises
        FROM SNMPv2-SMI;

mvRevisionNew MODULE-IDENTITY
    LAST-UPDATED "202607130000Z"
    ORGANIZATION "mibvendor parser bake-off"
    CONTACT-INFO "nobody@example.invalid"
    DESCRIPTION  "Newer half of a revision-shape fixture."
    REVISION     "202607130000Z"
    DESCRIPTION  "Adds a second object."
    REVISION     "202501010000Z"
    DESCRIPTION  "Initial fixture revision."
    ::= { enterprises 99995 }

mvRevisionValue OBJECT-TYPE
    SYNTAX      Integer32
    MAX-ACCESS  read-only
    STATUS      current
    DESCRIPTION "New-shape object retaining the shared descriptor."
    ::= { mvRevisionNew 1 }

mvRevisionExtra OBJECT-TYPE
    SYNTAX      Integer32
    MAX-ACCESS  read-only
    STATUS      current
    DESCRIPTION "Object added in the later revision."
    ::= { mvRevisionNew 2 }

END
