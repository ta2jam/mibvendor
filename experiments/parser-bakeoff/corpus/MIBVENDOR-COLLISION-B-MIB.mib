-- SPDX-License-Identifier: CC0-1.0
MIBVENDOR-COLLISION-B-MIB DEFINITIONS ::= BEGIN

IMPORTS
    MODULE-IDENTITY, OBJECT-TYPE, Integer32, enterprises
        FROM SNMPv2-SMI;

mvCollisionB MODULE-IDENTITY
    LAST-UPDATED "202607130000Z"
    ORGANIZATION "mibvendor parser bake-off"
    CONTACT-INFO "nobody@example.invalid"
    DESCRIPTION  "Second half of a symbol-collision fixture."
    REVISION     "202607130000Z"
    DESCRIPTION  "Initial fixture revision."
    ::= { enterprises 99997 }

mvSharedName OBJECT-TYPE
    SYNTAX      Integer32
    MAX-ACCESS  read-only
    STATUS      current
    DESCRIPTION "Same descriptor as another module, different OID."
    ::= { mvCollisionB 1 }

END
