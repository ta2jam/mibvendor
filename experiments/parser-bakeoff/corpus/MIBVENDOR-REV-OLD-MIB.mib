-- SPDX-License-Identifier: CC0-1.0
MIBVENDOR-REV-OLD-MIB DEFINITIONS ::= BEGIN

IMPORTS
    MODULE-IDENTITY, OBJECT-TYPE, Integer32, enterprises
        FROM SNMPv2-SMI;

mvRevisionOld MODULE-IDENTITY
    LAST-UPDATED "202501010000Z"
    ORGANIZATION "mibvendor parser bake-off"
    CONTACT-INFO "nobody@example.invalid"
    DESCRIPTION  "Older half of a revision-shape fixture."
    REVISION     "202501010000Z"
    DESCRIPTION  "Initial fixture revision."
    ::= { enterprises 99996 }

mvRevisionValue OBJECT-TYPE
    SYNTAX      Integer32
    MAX-ACCESS  read-only
    STATUS      current
    DESCRIPTION "Old-shape object."
    ::= { mvRevisionOld 1 }

END
