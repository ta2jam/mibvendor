-- SIGSCALE-PRODUCTS-MIB.mib:  SigScale Products

SIGSCALE-PRODUCTS-MIB DEFINITIONS ::= BEGIN

IMPORTS
    sigscaleModules, sigscaleProducts
        FROM SIGSCALE-SMI
    MODULE-IDENTITY
        FROM SNMPv2-SMI;

sigscaleProductsMIB MODULE-IDENTITY
    LAST-UPDATED "201806190000Z"
    ORGANIZATION "SigScale Global Inc."
    CONTACT-INFO
        "SigScale Global Inc.
         716/1/3 Dr. Danister de Silva Mawatha
         Colombo 00900
         Sri Lanka
         Tel: +94771231660
         E-mail: support@sigscale.org"
    DESCRIPTION
        "This module defines the object identifiers that are assigned to platforms as values for sysObjectID."
    ::= {sigscaleModules 3}

--

ocs OBJECT IDENTIFIER ::= {sigscaleProducts 1}

END
