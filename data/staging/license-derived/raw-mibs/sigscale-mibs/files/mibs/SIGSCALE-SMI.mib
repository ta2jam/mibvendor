-- SIGSCALE-SMI.mib:  SigScale Enterprise Structure of Management Information

SIGSCALE-SMI DEFINITIONS ::= BEGIN

IMPORTS
    MODULE-IDENTITY, OBJECT-IDENTITY, enterprises
        FROM SNMPv2-SMI;

sigscale MODULE-IDENTITY
    LAST-UPDATED "201806190000Z"
    ORGANIZATION "SigScale Global Inc."
    CONTACT-INFO
        "SigScale Global Inc.
         716/1/3 Dr. Danister de Silva Mawatha
         Colombo 00900
         Sri Lanka
         Tel: +94771231660
         E-mail: support@sigscale.org"
    DESCRIPTION
        "The Structure of Management Information for the SigScale Enterprise"
    ::= {enterprises 50386}  -- value assigned by IANA

sigscaleProducts OBJECT-IDENTITY
    STATUS   current
    DESCRIPTION
        "The root object identifier from which sysObjectID values may be assigned."
    ::= {sigscale 1}

sigscaleModules OBJECT-IDENTITY
    STATUS   current
    DESCRIPTION
        "The root object identifier from which MODULE-IDENTITY values may be assigned."
    ::= {sigscale 2}

sigscaleAgentCapability OBJECT-IDENTITY
    STATUS   current
    DESCRIPTION
        "The root object identifier from which AGENT-CAPABILITIES values may be assigned."
    ::= {sigscale 3}

sigscaleManagement OBJECT-IDENTITY
    STATUS   current
    DESCRIPTION
        "The main subtree for MIBs."
    ::= {sigscale 4}

sigscaleExperiment OBJECT-IDENTITY
    STATUS   current
    DESCRIPTION
        "The root object identifier from which experimental MIB values may be assigned."
    ::= {sigscale 5}

END
