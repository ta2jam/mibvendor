-- SIGSCALE-MODULES-MIB.mib:  SigScale Global Inc. Modules

SIGSCALE-MODULES-MIB DEFINITIONS ::= BEGIN

IMPORTS
    sigscaleModules, sigscaleManagement, sigscaleExperiment
        FROM SIGSCALE-SMI
    MODULE-IDENTITY
        FROM SNMPv2-SMI;

sigscaleModulesMIB MODULE-IDENTITY
    LAST-UPDATED "201806190000Z"
    ORGANIZATION "SigScale Global Inc."
    CONTACT-INFO
        "SigScale Global Inc.
         716/1/3 Dr. Danister de Silva Mawatha
         Colombo 00900
         Sri Lanka
         Tel: +94771231660
         E-mail: support@sigscale.org"
    DESCRIPTION
        "This module defines the object identifiers that are assigned as MODULE-IDENTITY."
    ::= {sigscaleModules 1}

--

sigscaleSMI                OBJECT IDENTIFIER ::= {sigscaleModules 2}
sigscaleProductsMIB        OBJECT IDENTIFIER ::= {sigscaleModules 3}
sigscaleTextualConvention  OBJECT IDENTIFIER ::= {sigscaleManagement 1}
ocsMIB                     OBJECT IDENTIFIER ::= {sigscaleManagement 51}
diameterBaseProtocolMIB    OBJECT IDENTIFIER ::= {sigscaleExperiment 1}
diameterCCAMIB             OBJECT IDENTIFIER ::= {sigscaleExperiment 2}
m3uaMIB                    OBJECT IDENTIFIER ::= {sigscaleExperiment 3}

END
