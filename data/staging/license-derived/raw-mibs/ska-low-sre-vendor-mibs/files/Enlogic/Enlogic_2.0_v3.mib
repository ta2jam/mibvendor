ENLOGIC-PDU-MIB DEFINITIONS ::= BEGIN

IMPORTS
    MODULE-IDENTITY, OBJECT-TYPE, NOTIFICATION-TYPE     FROM SNMPv2-SMI
    enterprises, Integer32, Unsigned32, IpAddress       FROM SNMPv2-SMI
    MODULE-COMPLIANCE, OBJECT-GROUP, NOTIFICATION-GROUP FROM SNMPv2-CONF
    TEXTUAL-CONVENTION, DisplayString, MacAddress, TruthValue  FROM SNMPv2-TC
    InetAddressType, InetAddress FROM INET-ADDRESS-MIB
    sysDescr,sysContact, sysName, sysLocation FROM RFC1213-MIB;

enlogic MODULE-IDENTITY

    LAST-UPDATED "202405030000Z"      -- May 03, 2024
   
    ORGANIZATION "Enlogic"
    
    CONTACT-INFO ""
	
	DESCRIPTION  "This MIB describes the SNMP functions of the Enlogic PDU. Support EE range"

	REVISION     "202405030000Z"      -- May 03, 2024
	DESCRIPTION  "
				 1.Deprecated two OIDs of Powershare table- pdupowershareSupportUpstreamSTATUS and pdupowershareSupportDownstreamSTATUS
				 2.Added 2 new OIDs in Powershare table- pduPowerShareBackupProtection and pduPowerShareOutput
				 3.Description updated for the above OIDs
				 4.Added pduExternalAssetManagerIndex OID in pduExternalAssetManagerTable
				 5.Added Hardware Version OID pduNamePlateHWVersion in pduNamePlate Table
				 6.Added two SNMP OIDs to display Power Factor for Total PDU and CB- pduUnitSTATUSPowerFactor and pduCircuitBreakerSTATUSPowerFactor
				 7.Added an OID pduUnitConfigTelnet in PduUnitConfigEntry Table"
	      

	REVISION     "202304250000Z"      -- Apr 25, 2023
	DESCRIPTION  "		 1.Added SNMP OID to display IPV6 address (Global address and Link address)of ETH0"		
	
	REVISION     "202205040000Z"      -- May 04, 2022	
	DESCRIPTION  "		 1.Corrected nodes of pduUnitSmartCabinetEntry as read and write "
	
	REVISION     "202202160000Z"      -- February 16, 2022
	DESCRIPTION  "
	             Added the following oids for digitalor
				 1.Added to get ulevel position in pduExternalAssetULevel
				 2.Added to get asset id in pduExternalAssetID
				 3.Added to get brand id in pduExternalAssetBrand
				 4.Added to get color of not connected tags in pduExternalAssetColorStandby
				 5.Added to get color of connected tags in pduExternalAssetColorConnected
				 6.Added to get orientation of asset module pduExternalMasterOrientation"
				 
	REVISION     "202109170000Z"      -- September 17, 2021
	DESCRIPTION  "
                 		 1.Added Digitalor Support
				 "			 
	REVISION     "202104210000Z"      -- April 21, 2021
	DESCRIPTION  "
                 		 1.Corrected as per MG-SOFT Compiler
				 "	
				 
	REVISION     "202101250000Z"      -- January 25, 2021
	DESCRIPTION  "
                 		 1.Modified description pduUnitStatusEnergy
				 2.Modified description pduUnitStatusResettableEnergy
				 "
				 
	REVISION     "202101060000Z"      -- January 06, 2021
	DESCRIPTION  "
                 1.Add disable all thresholds option in pduUnitConfigEnabledThresholds
				 2.Add disable daisychain in pduUnitConfigDaisyChainState
				 3.Add disable all thresholds option in pduOutletMeteredConfigEnabledThresholds
				 4.Add disable all thresholds option in pduCircuitBreakerConfigEnabledThresholds
				 5.Add disable all thresholds option in pduInputPhaseConfigCurrentEnabledThresholds
				 6.Add disable all thresholds option in pduInputPhaseConfigVoltageEnabledThresholds
				 7.Add description in pduUnitConfigSsh
				 8.Add description in pduExternalSensorConfigEnabledThresholds
				 9.Modified pduExternalSensorStatusAisle to Read-only
				 10.Modified discription in pduCircuitBreakerPropertiesCurrentRating
                 "		 
				 
	REVISION     "202101040000Z"      -- January 04, 2021
	DESCRIPTION  "Modify description of MIB node pduUnitSTATUSEnergy"
	
	REVISION     "202010300000Z"      -- October 30, 2020
	DESCRIPTION  "Modify description of MIB node pduExternalSensorNamePlateType and revoied card id OID"

	REVISION     "202009150000Z"      -- September 15, 2020
	DESCRIPTION  "Modify description of MIB node pduEhandleUserPinLength"

	REVISION     "202009090000Z"      -- September 9, 2020
	DESCRIPTION  "Modify description of MIB node pduEhandleControlCardAisle"

	REVISION     "202008280000Z"      -- August 28, 2020
	DESCRIPTION  "This MIB updated with ehandle support for EN2.0 PDU's"

	REVISION     "202006090000Z"      -- June 9, 2020
	DESCRIPTION  "This MIB updated with new five trap oid's required for EN2.0 PDU's"

	REVISION     "202005211000Z"      -- May 21, 2020
	DESCRIPTION  "This MIB updated PowerShare Descriptions"

	REVISION     "201904120000Z"      -- April 12, 2019
	DESCRIPTION  "
				 1. Add new trap named Powershare Information for EN2.0 PDU.
				 2. Ethernet information 
				 3. Add new trap named espNetworkUp for ES PDU
				 "

	REVISION     "201410280000Z"      -- October 28, 2014
	
	DESCRIPTION  "
				 1. Add Smart Cabinet related MIB nodes.
				 "

	REVISION     "201406050000Z"      -- June 5, 2014
	DESCRIPTION  "
				 1. Add new trap named espNetworkUp for ES PDU.
				 "

	REVISION     "201404300000Z"      -- April 30, 2014
	DESCRIPTION  "
				 1. Modify description of MIB node pduInputPhaseSTATUSCurrentState, pduInputPhaseSTATUSCurrent,
					pduInputPhaseSTATUSVoltage,pduInputPhaseSTATUSActivePower, pduInputPhaseSTATUSApparentPower
					and pduInputPhaseSTATUSPowerFactor.
				 "

	REVISION     "201306050000Z"      -- June 5, 2013
	DESCRIPTION  "
				 1. Change node pduExternalSensorSTATUSAisle to be writable.
				 "

	REVISION     "201305310000Z"      -- May 31, 2013
	DESCRIPTION  "
				 1. Add MIB node for daisy chain state. 
				 "

	REVISION     "201303280000Z"      -- March 28, 2013
	DESCRIPTION  "
				 1. Add one more attribute for all trap oids indicating pdu idx in case of daisy chain. 
				 2. Add one more MIB node in order to reset network management card          
				 "

	REVISION     "201303210000Z"      -- March 21, 2013
	DESCRIPTION  "
				 1. Add MIB node for external sensor unique identifier. 
				 2. Add MIB node for external sensor readings with higher Pricision.           
				 "

	REVISION     "201301240000Z"      -- January 24, 2013
	DESCRIPTION  "
				 1. change external sensor name doorContact to doorSwitch             
				 "

	REVISION     "201301060000Z"      -- January 6, 2013
	DESCRIPTION  "
				 1. change the enum value definition of external sensor threshold setting
				 2. Add a new node to enable/disable SSH connection  
				 3. Add one more external sensor unit              
				 "

	REVISION     "201212280000Z"      -- December 28, 2012
	DESCRIPTION  "
				 1. Add one more node to enable/disable sensor                
				 "

	REVISION     "201209280000Z"      -- September 28, 2012
	DESCRIPTION  "
				 1. Added additional indexes.
				 "
	
	REVISION     "201209250000Z"      -- September 25, 2012
	DESCRIPTION  "
				 1. Changed descriptions for STATUS readings.
				 "

	REVISION     "201209180000Z"      -- September 18, 2012
	DESCRIPTION  "
				 1. Changed descriptions for alarm thresholds.
				 2. Renamed pduOutletMeteredSTATUSEnergy to pduOutletMeteredSTATUSResettableEnergy.
				 3. Added pduUnitConfigOutletPeakPowerReset
				 "    

	REVISION     "201209130000Z"      -- September 13, 2012
	DESCRIPTION  "
				 1. Changed SYNTAX of pduUnitConfigUpperWarningThreshold SEQUENCE to Unsigned32
				 2. Changed SYNTAX of pduOutletSwitchedStateOnStartup to Integer32 
				 3. Changed SYNTAX of pduServerPingEnabled to TruthValue
				 4. Added trapsInformationIndex to SEQUENCE of TrapsInformationEntry  
				 "    
                  ::= { enterprises 38446 }

 
pdu  						OBJECT IDENTIFIER ::= { enlogic 1 }
pduNamePlate  					OBJECT IDENTIFIER ::= { pdu 1 }
pduUnit  					OBJECT IDENTIFIER ::= { pdu 2 }
pduInputPhase  					OBJECT IDENTIFIER ::= { pdu 3 }
pduCircuitBreaker  				OBJECT IDENTIFIER ::= { pdu 4 }
pduOutlet  					OBJECT IDENTIFIER ::= { pdu 5 }
pduExternalSensor  				OBJECT IDENTIFIER ::= { pdu 6 }
pduSmartCabinet  				OBJECT IDENTIFIER ::= { pdu 7 }
pduTraps					OBJECT IDENTIFIER ::= { pdu 8 }
pduEhandle					OBJECT IDENTIFIER ::= { pdu 9 }

-- Start pduNamePlate

pduNamePlateTableSize  OBJECT-TYPE
	SYNTAX 	Integer32 (1..256)
	MAX-ACCESS  	read-only
	STATUS 	current
	DESCRIPTION 
		"The total number of PDUs"
	::= { pduNamePlate 1 }

-- pduNamePlateTable
pduNamePlateTable  OBJECT-TYPE
	SYNTAX SEQUENCE OF PduNamePlateEntry
	MAX-ACCESS  	not-accessible
	STATUS 	current
	DESCRIPTION 
		"A table of PDU nameplate data"
	::= { pduNamePlate 2 }
	
pduNamePlateEntry  OBJECT-TYPE
	SYNTAX 	PduNamePlateEntry
	MAX-ACCESS  	not-accessible
	STATUS 	current
	DESCRIPTION 
		"Nameplate data from the PDU being queried. The numbers of entries equals the value of pduNamePlateTableSize."
	INDEX { pduNamePlateIndex }
	::= { pduNamePlateTable 1 }

PduNamePlateEntry ::= SEQUENCE {
	pduNamePlateIndex
		Integer32,
	pduNamePlateName
		DisplayString,
	pduNamePlateLocation
		DisplayString,
	pduNamePlateInetAddressType
		INTEGER,
	pduNamePlateIPAddress
		InetAddress,
	pduNamePlateInetNetMask
		InetAddress,
	pduNamePlateInetGateway
		InetAddress,
	pduNamePlateMACAddress
		MacAddress,
	pduNamePlateUTCTimeOffset
		DisplayString,
	pduNamePlateModelNumber
		DisplayString,
	pduNamePlatePartNumber
		DisplayString,
	pduNamePlateSerialNumber
		DisplayString,
	pduNamePlateDateofManufacture
		DisplayString,
	pduNamePlateFirmwareVersion
		DisplayString,
	pduNamePlateFirmwareVersionTimeStamp
		DisplayString,
	pduNamePlateType
		INTEGER,
	pduNamePlateIPV6Address
		DisplayString,
	pduNamePlateHWVersion
		DisplayString
	}

pduNamePlateIndex  OBJECT-TYPE
	SYNTAX 	Integer32 (1..256)
	MAX-ACCESS  	not-accessible
	STATUS 	current
	DESCRIPTION 
		"The index of the PDU nameplate table entry"
	::= { pduNamePlateEntry 1 }
	
pduNamePlateName  OBJECT-TYPE
	SYNTAX 	DisplayString
	MAX-ACCESS  	read-only
	STATUS 	current
	DESCRIPTION 
		"A user-defined string identifying the PDU"
	::= { pduNamePlateEntry 2 }
	
pduNamePlateLocation  OBJECT-TYPE
	SYNTAX 	DisplayString
	MAX-ACCESS  	read-only
	STATUS 	current
	DESCRIPTION 
		"A user-defined string identifying the location of PDU"
	::= { pduNamePlateEntry 3 }

pduNamePlateInetAddressType  OBJECT-TYPE
	SYNTAX 	INTEGER
	MAX-ACCESS  	read-only
	STATUS 	current
	DESCRIPTION 
		"The type of address format"
	::= { pduNamePlateEntry 4 }
	
pduNamePlateIPAddress  OBJECT-TYPE
	SYNTAX 	InetAddress
	MAX-ACCESS  	read-only
	STATUS 	current
	DESCRIPTION 
		"The current IP address. A value of 0.0.0.0 indicates an error or an unset option"
	::= { pduNamePlateEntry 5 }
	
pduNamePlateInetNetMask  OBJECT-TYPE
	SYNTAX 	InetAddress
	MAX-ACCESS  	read-only
	STATUS 	current
	DESCRIPTION 
		"The current netmask. A value of 0.0.0.0 indiates an error or an unset option"
	::= { pduNamePlateEntry 6 }
	
pduNamePlateInetGateway  OBJECT-TYPE
	SYNTAX 	InetAddress
	MAX-ACCESS  	read-only
	STATUS 	current
	DESCRIPTION 
		"The current gateway. A value of 0.0.0.0 indicates an error or an unset option"
	::= { pduNamePlateEntry 7 }
	
pduNamePlateMACAddress  OBJECT-TYPE
	SYNTAX 	MacAddress
	MAX-ACCESS  	read-only
	STATUS 	current
	DESCRIPTION 
		"The assigned MAC address for the PDU"
	::= { pduNamePlateEntry 8 }
	
pduNamePlateUTCTimeOffset  OBJECT-TYPE
	SYNTAX 	DisplayString
	MAX-ACCESS  	read-only
	STATUS 	current
	DESCRIPTION 
		"The difference in hours and minutes from Coordinated Universal 
		Time(UTC) for the time used in a particular time zone"
	::= { pduNamePlateEntry 9 }
	
pduNamePlateModelNumber  OBJECT-TYPE
	SYNTAX 	DisplayString
	MAX-ACCESS  	read-only
	STATUS 	current
	DESCRIPTION 
		"The PDU model number"
	::= { pduNamePlateEntry 10 }
pduNamePlatePartNumber  OBJECT-TYPE
	SYNTAX 	DisplayString
	MAX-ACCESS  	read-only
	STATUS 	current
	DESCRIPTION 
		"The PDU part number"
	::= { pduNamePlateEntry 11 }
	
pduNamePlateSerialNumber  OBJECT-TYPE
	SYNTAX 	DisplayString
	MAX-ACCESS  	read-only
	STATUS 	current
	DESCRIPTION 
		"The PDU serial number"
	::= { pduNamePlateEntry 12 }
	
pduNamePlateDateofManufacture  OBJECT-TYPE
	SYNTAX 	DisplayString
	MAX-ACCESS  	read-only
	STATUS 	current
	DESCRIPTION 
		"The date the PDU was manufactured in mm/dd/yyyy format"
	::= { pduNamePlateEntry 13 }

pduNamePlateFirmwareVersion  OBJECT-TYPE
	SYNTAX 	DisplayString
	MAX-ACCESS  	read-only
	STATUS 	current
	DESCRIPTION 
		"The PDU firmware version"
	::= { pduNamePlateEntry 14 }
	
pduNamePlateFirmwareVersionTimeStamp  OBJECT-TYPE
	SYNTAX 	DisplayString
	MAX-ACCESS  	read-only
	STATUS 	current
	DESCRIPTION 
		"Timestamp of when the PDU firmware was last updated"
	::= { pduNamePlateEntry 15 }
	
pduNamePlateType  OBJECT-TYPE
	SYNTAX 	INTEGER {singlePhase (1),delta (2),wye (3)}
	MAX-ACCESS  	read-only
	STATUS 	current
	DESCRIPTION 
		"The type of input"
	::= { pduNamePlateEntry 16 }
	
pduNamePlateIPV6Address  OBJECT-TYPE
	SYNTAX 	DisplayString
	MAX-ACCESS  	read-only
	STATUS 	current
	DESCRIPTION 
		"The current IPV6 address. A value of 0.0.0.0 indicates an error or an unset option"
	::= { pduNamePlateEntry 17 }

pduNamePlateHWVersion OBJECT-TYPE 
    SYNTAX DisplayString 
    MAX-ACCESS read-only 
    STATUS current 
    DESCRIPTION 
        "	" 
    ::= { pduNamePlateEntry 18 }
	
-- Start pduUnit

pduUnitTableSize  OBJECT-TYPE
	SYNTAX 	Integer32 (1..256)
	MAX-ACCESS  	read-only
	STATUS 	current
	DESCRIPTION 
		"The number of units."
	::= { pduUnit 1 }
	
pduUnitConfigTable  OBJECT-TYPE
	SYNTAX SEQUENCE OF PduUnitConfigEntry
	MAX-ACCESS  	not-accessible
	STATUS 	current
	DESCRIPTION 
		"A table of PDU configuration data"
	::= { pduUnit 2 }
	
pduUnitConfigEntry  OBJECT-TYPE
	SYNTAX 	PduUnitConfigEntry
	MAX-ACCESS  	not-accessible
	STATUS 	current
	DESCRIPTION 
		"Configuration data from the PDU being queried. The number of entries equals the value of pduUnitTableSize"
	INDEX { pduUnitConfigIndex }
	::= { pduUnitConfigTable 1 }

PduUnitConfigEntry ::= SEQUENCE {
	pduUnitConfigIndex
		Integer32,
	pduUnitConfigName
		DisplayString,
	pduUnitConfigLocation
		DisplayString,
	pduUnitConfigDisplayOrientation
		INTEGER,
	pduUnitConfigOledDisplayControl
		INTEGER,
	pduUnitConfigColdstartDelay
		Unsigned32,
	pduUnitConfigGlobalOutletStateOnStartup
		INTEGER,
	pduUnitConfigLowerCriticalThreshold
		Unsigned32,
	pduUnitConfigLowerWarningThreshold
		Unsigned32,
	pduUnitConfigUpperCriticalThreshold
		Unsigned32,
	pduUnitConfigUpperWarningThreshold
		Unsigned32,
	pduUnitConfigAlarmResetThreshold
		Unsigned32,
	pduUnitConfigAlarmStateChangeDelay
		Unsigned32,
	pduUnitConfigEnabledThresholds
		BITS,
	pduUnitConfigPeakPowerReset
		INTEGER,
	pduUnitConfigEnergyReset
		INTEGER,
	pduUnitConfigOutletPeakPowerReset
		INTEGER,
	pduUnitConfigOutletEnergyReset
		INTEGER,
	pduUnitConfigUsb
		INTEGER,
	pduUnitConfigSsh
		INTEGER,
	pduUnitConfigResetNetworkManagementCard
		INTEGER,
	pduUnitConfigDaisyChainState
		INTEGER,
	pduUnitConfigTelnet
		INTEGER		
	}

pduUnitConfigIndex  OBJECT-TYPE
	SYNTAX 	Integer32 (1..256)
	MAX-ACCESS  	not-accessible
	STATUS 	current
	DESCRIPTION 
		"The index of the PDU Unit Config Entry"
	::= { pduUnitConfigEntry 1 }
	
pduUnitConfigName  OBJECT-TYPE
	SYNTAX 	DisplayString
	MAX-ACCESS  	read-write
	STATUS 	current
	DESCRIPTION 
		"A user-defined string identifying the PDU"
	::= { pduUnitConfigEntry 2 }
	
pduUnitConfigLocation  OBJECT-TYPE
	SYNTAX 	DisplayString
	MAX-ACCESS  	read-write
	STATUS 	current
	DESCRIPTION 
		"A user-defined string identifying the location of the PDU"
	::= { pduUnitConfigEntry 3 }
	
pduUnitConfigDisplayOrientation  OBJECT-TYPE
	SYNTAX 	INTEGER {
		displayNormal (1),
		displayReverse (2)
	}
	MAX-ACCESS  	read-write
	STATUS 	current
	DESCRIPTION 
		"Indicates the intended physical orientation of the oLED display
		displayNormal (1) indicates normal orientation. 
		displayReverse (2) indicates upside down orientation"
	::= { pduUnitConfigEntry 4 }

pduUnitConfigOledDisplayControl  OBJECT-TYPE
	SYNTAX 	INTEGER {
		displayOff (1),
		displayOn (2)
	}
	MAX-ACCESS  	read-write
	STATUS 	current
	DESCRIPTION 
		"Used to turn oled display On or Off
		displayOff (1) to turn dispaly OFF. 
		displayOn (2) to turn dispaly ON"
	::= { pduUnitConfigEntry 5 }
	
pduUnitConfigColdstartDelay  OBJECT-TYPE
	SYNTAX 	Unsigned32 (0..3600)
	MAX-ACCESS  	read-write
	STATUS 	current
	DESCRIPTION 
		"The amount of time, specified in seconds, between when power 
		is provided to the PDU and when the PDU start providing basic master
		power to the outlets"
	::= { pduUnitConfigEntry 6 }
	
pduUnitConfigGlobalOutletStateOnStartup  OBJECT-TYPE
	SYNTAX 	INTEGER {
		off (0),
		on (1),
		lastKnownState (2)
	}
	MAX-ACCESS  	read-write
	STATUS 	current
	DESCRIPTION 
		"The outlet state on device startup; applies to all outlets 
		unless overridden at the outlet level"
	::= { pduUnitConfigEntry 7 }
	
pduUnitConfigLowerCriticalThreshold  OBJECT-TYPE
	SYNTAX 	Unsigned32
	MAX-ACCESS  	read-write
	STATUS 	current
	DESCRIPTION 
		"User-defined lower critical unit active power alarm threshold measured in Watts"
	::= { pduUnitConfigEntry 8 }
	
pduUnitConfigLowerWarningThreshold  OBJECT-TYPE
	SYNTAX 	Unsigned32
	MAX-ACCESS  	read-write
	STATUS 	current
	DESCRIPTION 
		"User-defined lower non-critical (warning) unit active power alarm threshold measured in Watts"
	::= { pduUnitConfigEntry 9 }
	
pduUnitConfigUpperCriticalThreshold  OBJECT-TYPE
	SYNTAX 	Unsigned32
	MAX-ACCESS  	read-write
	STATUS 	current
	DESCRIPTION 
		"User-defined upper critical unit active power alarm threshold measured in Watts"
	::= { pduUnitConfigEntry 10 }
	
pduUnitConfigUpperWarningThreshold  OBJECT-TYPE
	SYNTAX 	Unsigned32
	MAX-ACCESS  	read-write
	STATUS 	current
	DESCRIPTION 
		"User-defined upper non-critical (warning) unit active power alarm threshold measured in Watts"
	::= { pduUnitConfigEntry 11 }
	
pduUnitConfigAlarmResetThreshold  OBJECT-TYPE
	SYNTAX 	Unsigned32
	MAX-ACCESS  	read-write
	STATUS 	current
	DESCRIPTION 
		"The hysteresis used for deassertions in Watts"
	::= { pduUnitConfigEntry 12 }
	
pduUnitConfigAlarmStateChangeDelay  OBJECT-TYPE
	SYNTAX 	Unsigned32
	MAX-ACCESS  	read-write
	STATUS 	current
	DESCRIPTION 
		"The delay measured in samples before a state is asserted. If the value is zero, then the state is asserted as soon as it is detected; if it is non-zero, say n, then the assertion condition must exist for n+1 consecutive samples before the corresponding assertion event is reported."
	::= { pduUnitConfigEntry 13 }
	
pduUnitConfigEnabledThresholds  OBJECT-TYPE
	SYNTAX 	BITS {
		lowerCritical (0),
		lowerWarning (1),
		upperWarning  (2),
		upperCritical (3),
		disableall (4)
	}
	MAX-ACCESS  	read-write
	STATUS 	current
	DESCRIPTION 
		"A bit string indicating which alarm thresholds are enabled.Setting this
		 OID disableall(4) will disable all the thresholds."
	::= { pduUnitConfigEntry 14 }
	
pduUnitConfigPeakPowerReset  OBJECT-TYPE
	SYNTAX 	INTEGER {
		noOperation (1),
		reset (2)
	}
	MAX-ACCESS  	read-write
	STATUS 	current
	DESCRIPTION 
		"Setting this OID to reset (2) will cause the existing peak power value 
		to be replaced by the current load power value. Getting this OID will 
		do nothing and return the noOperation(1) value. "
	::= { pduUnitConfigEntry 15 }
	
pduUnitConfigEnergyReset  OBJECT-TYPE
	SYNTAX 	INTEGER {
		noOperation (1),
		reset (2),
		notSupported (3)
	}
	MAX-ACCESS  	read-write
	STATUS 	current
	DESCRIPTION 
		"Setting this OID to reset (2) will cause the device energy meter value 
		to be reset to zero. Getting this OID in models that support this 
		feature will do nothing and return the noOperation(1) value. Models 
		that do not support this feature will respond to this OID with a 
		value of notSupported (3). Attempts to set this OID in these models will fail. "
	::= { pduUnitConfigEntry 16 }

pduUnitConfigOutletPeakPowerReset  OBJECT-TYPE
	SYNTAX 	INTEGER {
		noOperation (1),
		reset (2),
		notSupported (3)
	}
	MAX-ACCESS  	read-write
	STATUS 	current
	DESCRIPTION 
		"Setting this OID to reset (2) will cause the outlet peak power meter value 
		to be reset to zero. Getting this OID in models that support this 
		feature will do nothing and return the noOperation(1) value. Models 
		that do not support this feature will respond to this OID with a 
		value of notSupported (3). Attempts to set this OID in these models will fail. "
	::= { pduUnitConfigEntry 17 }

pduUnitConfigOutletEnergyReset  OBJECT-TYPE
	SYNTAX 	INTEGER {
		noOperation (1),
		reset (2),
		notSupported (3)
	}
	MAX-ACCESS  	read-write
	STATUS 	current
	DESCRIPTION 
		"Setting this OID to reset (2) will cause the outlet energy meter value 
		to be reset to zero. Getting this OID in models that support this 
		feature will do nothing and return the noOperation(1) value. Models 
		that do not support this feature will respond to this OID with a 
		value of notSupported (3). Attempts to set this OID in these models will fail. "
	::= { pduUnitConfigEntry 18 }

pduUnitConfigUsb  OBJECT-TYPE
	SYNTAX 	INTEGER {
		off (0),
		on (1)
	}
	MAX-ACCESS  	read-write
	STATUS 	current
	DESCRIPTION 
		"Setting this OID to off(0) will disable the USB port.  Setting this OID to on(1) will enable the USB port."
	::= { pduUnitConfigEntry 19 }

pduUnitConfigSsh  OBJECT-TYPE
	SYNTAX 	INTEGER {
		off (0),
		on (1)
	}
	MAX-ACCESS  	read-write
	STATUS 	current
	DESCRIPTION 
		"Setting this OID to off(0) will disable the SSH connection.  Setting this OID to on(1) will enable the SSH connection.
		 Changes made will take effect only after reboot."
	::= { pduUnitConfigEntry 20 }
	
pduUnitConfigResetNetworkManagementCard  OBJECT-TYPE
	SYNTAX 	INTEGER {
		noOperation (0),
		reset (1)
	}
	MAX-ACCESS  	read-write
	STATUS 	current
	DESCRIPTION 
		"Getting this OID will return noOperation(0). Setting this OID to reset(1) will reset NMC.
        	 While resetting through grouping,grouping should  be done in descending order"
	::= { pduUnitConfigEntry 21 }
	
pduUnitConfigDaisyChainState	OBJECT-TYPE
	SYNTAX 	INTEGER {
		daisychainqna (0),
		daisychainrna (1)
	}
	MAX-ACCESS  	read-write
	STATUS 	current
	DESCRIPTION 
		"Setting this OID to 0 will enable daisychain qna mode.
		 Setting this OID to 1 will enable daisychain rna mode. Should be applied on last pdu in DaisyChain"
	::= { pduUnitConfigEntry 22 }
	 
pduUnitConfigTelnet  OBJECT-TYPE
	SYNTAX 	INTEGER {
		off (0),
		on (1)
	}
	MAX-ACCESS  	read-write
	STATUS 	current
	DESCRIPTION 
		"Setting this OID to off(0) will disable the Telnet connection.  Setting this OID to on(1) will enable the Telnet connection.
		 Changes made will take effect only after reboot."
	::= { pduUnitConfigEntry 23 }
			
pduUnitPropertiesTable  OBJECT-TYPE
	SYNTAX SEQUENCE OF PduUnitPropertiesEntry
	MAX-ACCESS  	not-accessible
	STATUS 	current
	DESCRIPTION 
		"A table of PDU properties"
	::= { pduUnit 3 }
	
pduUnitPropertiesEntry  OBJECT-TYPE
	SYNTAX 	PduUnitPropertiesEntry
	MAX-ACCESS  	not-accessible
	STATUS 	current
	DESCRIPTION 
		"A unit properties entry containing objects for a particular unit."
	INDEX { pduUnitPropertiesIndex }
	::= { pduUnitPropertiesTable 1 }

PduUnitPropertiesEntry ::= SEQUENCE {
	pduUnitPropertiesIndex
		Integer32,
	pduUnitPropertiesName
		DisplayString,
	pduUnitPropertiesOutletCount
		Integer32,
	pduUnitPropertiesSwitchedOutletCount
		Integer32,
	pduUnitPropertiesMeteredOutletCount
		Integer32,
	pduUnitPropertiesInputPhaseCount
		Integer32,
	pduUnitPropertiesCircuitBreakerCount
		Integer32,
	pduUnitPropertiesMaxExternalSensorCount
		Integer32,
	pduUnitPropertiesConnExternalSensorCount
		Integer32,
	pduUnitPropertiesRatedVoltage
		DisplayString,
	pduUnitPropertiesRatedMaxCurrent
		DisplayString,
	pduUnitPropertiesRatedFrequency
		DisplayString,
	pduUnitPropertiesRatedPower
		DisplayString,
	pduUnitPropertiesOrientation
		INTEGER,
	pduUnitPropertiesOutletLayout
		INTEGER,
	pduUnitPropertiesDaisyChainMemberType
		INTEGER
	}

pduUnitPropertiesIndex  OBJECT-TYPE
	SYNTAX 	Integer32 (1..256)
	MAX-ACCESS  	not-accessible
	STATUS 	current
	DESCRIPTION 
		"The index of the PDU properties table entry"
	::= { pduUnitPropertiesEntry 1 }
	
pduUnitPropertiesName  OBJECT-TYPE
	SYNTAX 	DisplayString
	MAX-ACCESS  	read-only
	STATUS 	current
	DESCRIPTION 
		"A user-defined string identifying the PDU"
	::= { pduUnitPropertiesEntry 2 }
	
pduUnitPropertiesOutletCount  OBJECT-TYPE
	SYNTAX 	Integer32 (1..256)
	MAX-ACCESS  	read-only
	STATUS 	current
	DESCRIPTION 
		"The total number of outlets on the PDU"
	::= { pduUnitPropertiesEntry 3 }
	
pduUnitPropertiesSwitchedOutletCount  OBJECT-TYPE
	SYNTAX 	Integer32 (1..256)
	MAX-ACCESS  	read-only
	STATUS 	current
	DESCRIPTION 
		"The total number of switched outlets on the PDU"
	::= { pduUnitPropertiesEntry 4 }
	
pduUnitPropertiesMeteredOutletCount  OBJECT-TYPE
	SYNTAX 	Integer32 (1..256)
	MAX-ACCESS  	read-only
	STATUS 	current
	DESCRIPTION 
		"The total number of metered outlets on the PDU"
	::= { pduUnitPropertiesEntry 5 }
	
pduUnitPropertiesInputPhaseCount  OBJECT-TYPE
	SYNTAX 	Integer32 (1..256)
	MAX-ACCESS  	read-only
	STATUS 	current
	DESCRIPTION 
		"The total number of phases on the PDU"
	::= { pduUnitPropertiesEntry 6 }

pduUnitPropertiesCircuitBreakerCount  OBJECT-TYPE
	SYNTAX 	Integer32 (0..255)
	MAX-ACCESS  	read-only
	STATUS 	current
	DESCRIPTION 
		"The total number of circuit breaker on the PDU"
	::= { pduUnitPropertiesEntry 7 }
	
pduUnitPropertiesMaxExternalSensorCount  OBJECT-TYPE
	SYNTAX 	Integer32 (0..255)
	MAX-ACCESS  	read-only
	STATUS 	current
	DESCRIPTION 
		"The maximum number of external sensors that can be connected to the PDU"
	::= { pduUnitPropertiesEntry 8 }
	
pduUnitPropertiesConnExternalSensorCount  OBJECT-TYPE
	SYNTAX 	Integer32 (0..255)
	MAX-ACCESS  	read-only
	STATUS 	current
	DESCRIPTION 
		"The current number of external sensors connected to the PDU"
	::= { pduUnitPropertiesEntry 9 }
	
pduUnitPropertiesRatedVoltage  OBJECT-TYPE
	SYNTAX 	DisplayString
	MAX-ACCESS  	read-only
	STATUS 	current
	DESCRIPTION 
		"The PDU voltage rating in Volts"
	::= { pduUnitPropertiesEntry 10 }
	
pduUnitPropertiesRatedMaxCurrent  OBJECT-TYPE
	SYNTAX 	DisplayString
	MAX-ACCESS  	read-only
	STATUS 	current
	DESCRIPTION 
		"The PDU current rating in Amps"
	::= { pduUnitPropertiesEntry 11 }
	
pduUnitPropertiesRatedFrequency  OBJECT-TYPE
	SYNTAX 	DisplayString
	MAX-ACCESS  	read-only
	STATUS 	current
	DESCRIPTION 
		"The PDU frequency rating in Hz"
	::= { pduUnitPropertiesEntry 12 }
	
pduUnitPropertiesRatedPower  OBJECT-TYPE
	SYNTAX 	DisplayString
	MAX-ACCESS  	read-only
	STATUS 	current
	DESCRIPTION 
		"The PDU VA (VoltAmps) rating."
	::= { pduUnitPropertiesEntry 13 }
	
pduUnitPropertiesOrientation  OBJECT-TYPE
	SYNTAX 	INTEGER {
		horizontal (1),
		vertical (2)
	}
	MAX-ACCESS  	read-only
	STATUS 	current
	DESCRIPTION 
		"The PDU orientation "
	::= { pduUnitPropertiesEntry 14 }
	
pduUnitPropertiesOutletLayout  OBJECT-TYPE
	SYNTAX 	INTEGER {
		seqPhaseToNuetral (1),
		seqPhaseToPhase (2),
		seqPhToNeu21PhToPh (3),
		seqPhToPhGrouped (4),
		seqPhToNGrouped (5),
		seqPToN1516PToPGrouped (6),
		seqPhToPh2xGrouped (7),
		seqPhToN2xGrouped (8),
		seqNotApplicable (9)
	}
	MAX-ACCESS  	read-only
	STATUS 	current
	DESCRIPTION 
		"The outlet layout for the PDU. Getting this OID will return outlet layout for the device.
		seqPhaseToNeutral(1) indicates outlet layout as follows:
		1:1-N,2:2-N,3:3-N,4:1-N,5:2-N,...
		seqPhaseToPhase(2) indicates outlet layout as follows:
		1:1-2,2:2-3,3:3-1,4:1-2,5:2-3,...
		seqPhToNeu21PhToPh(3) indicates outlet layout as follows:
		1:1-N,2:2-N...21:3-N,22:1-2,23:2-3,24:3-1,...
		seqPhToPhGrouped(4) indicates outlet layout as follows:
		This unit has 3 outlet groups.  Group 1:1-2, Group 2:2-3, Group 3:3-1.
		seqPhToNGrouped(5) indicates outlet layout as follows:
		This unit has 3 outlet groups.  Group 1:1-N, Group 2:2-N, Group 3:3-N.
		seqPToN1516PToPGrouped(6) indicates outlet layout as follows:
		This unit has 4 outlet groups. Group 1 (Outlets 1-14):1-2,
		Group 2 (Outlets 15-16):1-N, Group 3:2-3, Group 4:3-1.
		seqPhToPh2xGrouped(7) indicates outlet layout as follows:
		This unit has 6 outlet groups.  Group 1:1-2, Group 2:1-2, Group 3:2-3,
		Group 4:2-3, Group 5:3-1, Group 6:3-1.
		seqPhToN2xGrouped(8) indicates outlet layout as follows:
		This unit has 6 outlet groups.  Group 1:1-N, Group 2:1-N, Group 3:2-N,
		Group 4:2-N, Group 5:3-N, Group 6:3-N.
		seqNotApplicable(9):"
	::= { pduUnitPropertiesEntry 15 }
	
pduUnitPropertiesDaisyChainMemberType  OBJECT-TYPE
	SYNTAX 	INTEGER {
		standalone (1),
		parent (2),
		child (3)
	}
	MAX-ACCESS  	read-only
	STATUS 	current
	DESCRIPTION 
		"The daisy-chain member type"
	::= { pduUnitPropertiesEntry 16 }
		
pduUnitSTATUSTable  OBJECT-TYPE
	SYNTAX SEQUENCE OF PduUnitSTATUSEntry
	MAX-ACCESS  	not-accessible
	STATUS 	current
	DESCRIPTION 
		"A table of PDU STATUS information"
	::= { pduUnit 4 }
	
pduUnitSTATUSEntry  OBJECT-TYPE
	SYNTAX 	PduUnitSTATUSEntry
	MAX-ACCESS  	not-accessible
	STATUS 	current
	DESCRIPTION 
		"STATUS information from the PDU being queried"
	INDEX { pduUnitSTATUSIndex }
	::= { pduUnitSTATUSTable 1 }

PduUnitSTATUSEntry ::= SEQUENCE {
	pduUnitSTATUSIndex
		Integer32,
	pduUnitSTATUSName
		DisplayString,
	pduUnitSTATUSLoadState
		INTEGER,
	pduUnitSTATUSActivePower
		Integer32,
	pduUnitSTATUSApparentPower
		Integer32,
	pduUnitSTATUSPeakPower
		Integer32,
	pduUnitSTATUSPeakPowerTimestamp
		DisplayString,
	pduUnitSTATUSPeakPowerStartTime
		DisplayString,
	pduUnitSTATUSEnergy
		Integer32,
	pduUnitSTATUSResettableEnergy
		Integer32,
	pduUnitSTATUSEnergyStartTime
		DisplayString,
	pduUnitSTATUSOutletsEnergyStartTime
		DisplayString,
	pduUnitSTATUSPowerFactor
		Integer32
		
	}

pduUnitSTATUSIndex  OBJECT-TYPE
	SYNTAX 	Integer32 (1..256)
	MAX-ACCESS  	not-accessible
	STATUS 	current
	DESCRIPTION 
		"The index of the PDU STATUS table entry"
	::= { pduUnitSTATUSEntry 1 }
	
pduUnitSTATUSName  OBJECT-TYPE
	SYNTAX 	DisplayString
	MAX-ACCESS  	read-only
	STATUS 	current
	DESCRIPTION 
		"A user-defined string identifying the PDU"
	::= { pduUnitSTATUSEntry 2 }
	
pduUnitSTATUSLoadState  OBJECT-TYPE
	SYNTAX 	INTEGER {
		upperCritical (1),
		upperWarning (2),
		lowerWarning (3),
		lowerCritical (4),
		normal (5)
	}
	MAX-ACCESS  	read-only
	STATUS 	current
	DESCRIPTION 
		"Returns the present load STATUS of the PDU based on Active Power."
	::= { pduUnitSTATUSEntry 3 }
	
pduUnitSTATUSActivePower  OBJECT-TYPE
	SYNTAX 	Integer32
	MAX-ACCESS  	read-only
	STATUS 	current
	DESCRIPTION 
		"Returns power consumption, in Watts(W), 
		of the PDU being queried."
	::= { pduUnitSTATUSEntry 4 }

pduUnitSTATUSApparentPower  OBJECT-TYPE
	SYNTAX 	Integer32
	MAX-ACCESS  	read-only
	STATUS 	current
	DESCRIPTION 
		"Returns power consumption, in Volt-Amps(VA) 
		of the PDU load being queried."
	::= { pduUnitSTATUSEntry 5 }
	
pduUnitSTATUSPeakPower  OBJECT-TYPE
	SYNTAX 	Integer32
	MAX-ACCESS  	read-only
	STATUS 	current
	DESCRIPTION 
		"Returns peak power consumption, in Watts(W), 
		of the PDU being queried."
	::= { pduUnitSTATUSEntry 6 }
	
pduUnitSTATUSPeakPowerTimestamp  OBJECT-TYPE
	SYNTAX 	DisplayString
	MAX-ACCESS  	read-only
	STATUS 	current
	DESCRIPTION 
		"Indicates the date and time that peak power consumption occurred"
	::= { pduUnitSTATUSEntry 7 }
	
pduUnitSTATUSPeakPowerStartTime  OBJECT-TYPE
	SYNTAX 	DisplayString
	MAX-ACCESS  	read-only
	STATUS 	current
	DESCRIPTION 
		"Indicates the date and time of the last device peak power reset"
	::= { pduUnitSTATUSEntry 8 }
	
pduUnitSTATUSEnergy  OBJECT-TYPE
	SYNTAX 	Integer32
	MAX-ACCESS  	read-only
	STATUS 	current
	DESCRIPTION 
		"Returns total energy consumed, in WattHours(Wh)/100, of the PDU over its lifetime.
		Example:Total Energy=1234Wh ,pduUnitSTATUSEnergy will be 12."		
	::= { pduUnitSTATUSEntry 9 }

pduUnitSTATUSResettableEnergy  OBJECT-TYPE
	SYNTAX 	Integer32
	MAX-ACCESS  	read-only
	STATUS 	current
	DESCRIPTION 
		"A user resettable energy meter measuring PDU energy consumption 
		 in WattHours(Wh)/100.
		 Example:Total Energy=1234Wh ,pduUnitStatusResettableEnergy will be 12."
	::= { pduUnitSTATUSEntry 10 }
	
pduUnitSTATUSEnergyStartTime  OBJECT-TYPE
	SYNTAX 	DisplayString
	MAX-ACCESS  	read-only
	STATUS 	current
	DESCRIPTION 
		"Indicates the date and time of the last device energy meter reset"
	::= { pduUnitSTATUSEntry 11 }
	
pduUnitSTATUSOutletsEnergyStartTime  OBJECT-TYPE
	SYNTAX 	DisplayString
	MAX-ACCESS  	read-only
	STATUS 	current
	DESCRIPTION 
		"Indicates the date and time of the last outlets energy meter reset"
	::= { pduUnitSTATUSEntry 12 }
	
pduUnitSTATUSPowerFactor  OBJECT-TYPE
	SYNTAX 	Integer32
	MAX-ACCESS  	read-only
	STATUS 	current
	DESCRIPTION 
		"Displays the PDU Power Factor (ratio of active power to apparent power) in hundredths.
		Example: Power Factor=1, pduUnitSTATUSPowerFactor displays as 100"
	::= { pduUnitSTATUSEntry 13 }

--     ======Powershare STATUS==========
		-- 1.3.6.1.4.1.38446.1.2.5
		pdupowershareTable OBJECT-TYPE
			SYNTAX SEQUENCE OF PdupowershareEntry
			MAX-ACCESS not-accessible
			STATUS current
			DESCRIPTION
				"Aggregate Object with number of entries equal to number of PDUs and Power share "
    ::= { pduUnit 5}

		pdupowershareEntry OBJECT-TYPE
			SYNTAX PdupowershareEntry
			MAX-ACCESS not-accessible
			STATUS current
			DESCRIPTION
				"The Power share entry containing the avaliable, input, output etc."
			INDEX { pdupowershareIndex }
			::= { pdupowershareTable 1 }

		
		PdupowershareEntry ::=
			SEQUENCE { 
				pdupowershareIndex
					INTEGER,
				pdupowershareSupportUpstreamSTATUS
					INTEGER,
				pdupowershareSupportDownstreamSTATUS		
					INTEGER,	
				pdupowershareOptMode
					INTEGER,
				pdupowershareFunc
					INTEGER,
				pduPowerShareBackupProtection
					INTEGER,
				pduPowerShareOutput
					INTEGER
			 }

		pdupowershareIndex OBJECT-TYPE
			SYNTAX INTEGER (1..4)
			MAX-ACCESS read-only
			STATUS current
			DESCRIPTION
				"The index of the PDU Power share table entry"
			::= { pdupowershareEntry 1 }

	
		pdupowershareSupportUpstreamSTATUS OBJECT-TYPE
			SYNTAX INTEGER
				{
				notAvailable(0),
				available(1)
				}
			MAX-ACCESS read-only
			STATUS current
			DESCRIPTION
				"Deprecated because of newly added OID"
			::= { pdupowershareEntry 2}		
			
		pdupowershareSupportDownstreamSTATUS OBJECT-TYPE
			SYNTAX INTEGER
				{
				notAvailable(0),
				available(1)
				}
			MAX-ACCESS read-only
			STATUS current
			DESCRIPTION
				"Deprecated because of newly added OID"
			::= { pdupowershareEntry 3 }	
	
		pdupowershareOptMode OBJECT-TYPE
			SYNTAX INTEGER
				{
				backupPower(0),
				mainPower(1)
				}
			MAX-ACCESS read-only
			STATUS current
			DESCRIPTION
				"Operating power STATUS. "
			::= { pdupowershareEntry 4 }	
		
		pdupowershareFunc OBJECT-TYPE
			SYNTAX INTEGER
				{
				off(0),
				on(1)
				}
		MAX-ACCESS	read-write
		STATUS	current
		DESCRIPTION
			"Setting this OID to off(0) will disable the Powershare function.
			 Setting this OID to on(1) will enable the Powershare function."
		::= {pdupowershareEntry 5 }
	
		pduPowerShareBackupProtection OBJECT-TYPE
			SYNTAX INTEGER
				{
				notAvailable(0),
				available(1)
				}
			MAX-ACCESS read-only
			STATUS current
			DESCRIPTION
				"Power share support from either of the adjacent PDUs "
			::= { pdupowershareEntry 6}		
			
		pduPowerShareOutput OBJECT-TYPE
			SYNTAX INTEGER
				{
				notAvailable(0),
				available(1)
				}
			MAX-ACCESS read-only
			STATUS current
			DESCRIPTION
				"Power share support to either of the adjacent PDUs "
			::= { pdupowershareEntry 7}	
		
-- Start pduInputPhase
pduInputPhaseTableSize  OBJECT-TYPE
	SYNTAX 	Integer32 (1..256)
	MAX-ACCESS  	read-only
	STATUS 	current
	DESCRIPTION 
		"The number of PDU Input Phases "
	::= { pduInputPhase 1 }
	
pduInputPhaseConfigTable  OBJECT-TYPE
	SYNTAX SEQUENCE OF PduInputPhaseConfigEntry
	MAX-ACCESS  	not-accessible
	STATUS 	current
	DESCRIPTION 
		"A table of PDU Input Phase configuration data"
	::= { pduInputPhase 2 }
	
pduInputPhaseConfigEntry  OBJECT-TYPE
	SYNTAX 	PduInputPhaseConfigEntry
	MAX-ACCESS  	not-accessible
	STATUS 	current
	DESCRIPTION 
		"An input phase entry containing objects for a particular input phase."
	INDEX { pduUnitConfigIndex, pduInputPhaseConfigIndex }
	::= { pduInputPhaseConfigTable 1 }

PduInputPhaseConfigEntry ::= SEQUENCE {
	pduInputPhaseConfigIndex
		Integer32,
	pduInputPhaseConfigCount
		Integer32,
	pduInputPhaseConfigOverloadRestriction
		INTEGER,
	pduInputPhaseConfigCurrentLowerCriticalThreshold
		Unsigned32,
	pduInputPhaseConfigCurrentLowerWarningThreshold
		Unsigned32,
	pduInputPhaseConfigCurrentUpperCriticalThreshold
		Unsigned32,
	pduInputPhaseConfigCurrentUpperWarningThreshold
		Unsigned32,
	pduInputPhaseConfigVoltageLowerCriticalThreshold
		Unsigned32,
	pduInputPhaseConfigVoltageLowerWarningThreshold
		Unsigned32,
	pduInputPhaseConfigVoltageUpperCriticalThreshold
		Unsigned32,
	pduInputPhaseConfigVoltageUpperWarningThreshold
		Unsigned32,
	pduInputPhaseConfigCurrentAlarmResetThreshold
		Unsigned32,
	pduInputPhaseConfigCurrentAlarmStateChangeDelay
		Integer32,
	pduInputPhaseConfigCurrentEnabledThresholds
		BITS,
	pduInputPhaseConfigVoltageAlarmResetThreshold
		Unsigned32,
	pduInputPhaseConfigVoltageAlarmStateChangeDelay
		Integer32,
	pduInputPhaseConfigVoltageEnabledThresholds
		BITS
	}

pduInputPhaseConfigIndex  OBJECT-TYPE
	SYNTAX 	Integer32 (1..256)
	MAX-ACCESS  	not-accessible
	STATUS 	current
	DESCRIPTION 
		"The index of the PDU Input Phase configuration table entry"
	::= { pduInputPhaseConfigEntry 1 }
	
pduInputPhaseConfigCount  OBJECT-TYPE
	SYNTAX 	Integer32 (1..256)
	MAX-ACCESS  	read-only
	STATUS 	current
	DESCRIPTION 
		"The total number of Input Phases"
	::= { pduInputPhaseConfigEntry 2 }
	
pduInputPhaseConfigOverloadRestriction  OBJECT-TYPE
	SYNTAX 	INTEGER {
		alwaysAllowTurnOn (1),
		restrictOnUpperWarning (2),
		restrictOnUpperCritical (3),
		notSupported (4)
	}
	MAX-ACCESS  	read-write
	STATUS 	current
	DESCRIPTION 
		"This OID controls the behavior of a Switched PDU Input Phase when an 
		overload condition is possible and additional outlets are requested 
		to be turned on. Setting this OID to alwaysAllowTurnON (1) will always 
		allow the outlets on the corresponding Input Phase to turn on. Setting 
		this OID to restrictOnUpperWarning (2) will not allow outlets on the 
		corresponding Input Phase to turn on if the 
		pduInputPhaseConfigUpperWarningThreshold OID is exceeded. Setting 
		this OID to restrictOnUpperCritical (3) will not allow outlets on 
		the corresponding Input Phase to turn on if the 
		pduInputPhaseConfigUpperCriticalThreshold OID is exceeded. Models 
		that do not support this feature will respond to this OID with a 
		value of notSupported (4). Attempts to set this OID in these 
		models will fail. "
	::= { pduInputPhaseConfigEntry 3 }
	
pduInputPhaseConfigCurrentLowerCriticalThreshold  OBJECT-TYPE
	SYNTAX 	Unsigned32
	MAX-ACCESS  	read-write
	STATUS 	current
	DESCRIPTION 
		"User-defined lower critical input phase current alarm threshold in hundredths of Amps(A)."
	::= { pduInputPhaseConfigEntry 4 }
	
pduInputPhaseConfigCurrentLowerWarningThreshold  OBJECT-TYPE
	SYNTAX 	Unsigned32
	MAX-ACCESS  	read-write
	STATUS 	current
	DESCRIPTION 
		"User-defined lower non-critical (warning) input phase current alarm threshold in hundredths of Amps(A)."
	::= { pduInputPhaseConfigEntry 5 }
	
pduInputPhaseConfigCurrentUpperCriticalThreshold  OBJECT-TYPE
	SYNTAX 	Unsigned32
	MAX-ACCESS  	read-write
	STATUS 	current
	DESCRIPTION 
		"User-defined upper critical input phase current alarm threshold in hundredths of Amps(A)."
	::= { pduInputPhaseConfigEntry 6 }
	
pduInputPhaseConfigCurrentUpperWarningThreshold  OBJECT-TYPE
	SYNTAX 	Unsigned32
	MAX-ACCESS  	read-write
	STATUS 	current
	DESCRIPTION 
		"User-defined upper non-critical (warning) input phase current alarm threshold in hundredths of Amps(A)."
	::= { pduInputPhaseConfigEntry 7 }

pduInputPhaseConfigVoltageLowerCriticalThreshold  OBJECT-TYPE
	SYNTAX 	Unsigned32
	MAX-ACCESS  	read-write
	STATUS 	current
	DESCRIPTION 
		"User-defined lower critical input phase voltage alarm threshold in Volts(V)."
	::= { pduInputPhaseConfigEntry 8 }
	
pduInputPhaseConfigVoltageLowerWarningThreshold  OBJECT-TYPE
	SYNTAX 	Unsigned32
	MAX-ACCESS  	read-write
	STATUS 	current
	DESCRIPTION 
		"User-defined lower non-critical (warning) input phase voltage alarm threshold in Volts(V)."
	::= { pduInputPhaseConfigEntry 9 }
	
pduInputPhaseConfigVoltageUpperCriticalThreshold  OBJECT-TYPE
	SYNTAX 	Unsigned32
	MAX-ACCESS  	read-write
	STATUS 	current
	DESCRIPTION 
		"User-defined upper critical input phase voltage alarm threshold in Volts(V)."
	::= { pduInputPhaseConfigEntry 10 }
	
pduInputPhaseConfigVoltageUpperWarningThreshold  OBJECT-TYPE
	SYNTAX 	Unsigned32
	MAX-ACCESS  	read-write
	STATUS 	current
	DESCRIPTION 
		"User-defined upper non-critical (warning) input phase voltage alarm threshold in Volts(V)."
	::= { pduInputPhaseConfigEntry 11 }
	
pduInputPhaseConfigCurrentAlarmResetThreshold  OBJECT-TYPE
	SYNTAX 	Unsigned32
	MAX-ACCESS  	read-write
	STATUS 	current
	DESCRIPTION 
		"The hysteresis used for current alarm deassertions in hundredths of Amps(A)."
	::= { pduInputPhaseConfigEntry 12 }
	
pduInputPhaseConfigCurrentAlarmStateChangeDelay  OBJECT-TYPE
	SYNTAX 	Integer32
	MAX-ACCESS  	read-write
	STATUS 	current
	DESCRIPTION 
		"The delay measured in samples before a current state is asserted. If the 
		value is zero, then the state is asserted as soon as it is 
		detected; if it is non-zero, say n, then the assertion condition 
		must exist for n+1 consecutive samples before the corresponding 
		assertion event is reported. "
	::= { pduInputPhaseConfigEntry 13 }
	
pduInputPhaseConfigCurrentEnabledThresholds  OBJECT-TYPE
	SYNTAX 	BITS {
		lowerCritical (0),
		lowerWarning (1),
		upperWarning (2),
		upperCritical (3)
	}
	MAX-ACCESS  	read-write
	STATUS 	current
	DESCRIPTION 
		"A bit string indicating which current alarm thresholds are enabled."
	::= { pduInputPhaseConfigEntry 14 }
	
pduInputPhaseConfigVoltageAlarmResetThreshold  OBJECT-TYPE
	SYNTAX 	Unsigned32
	MAX-ACCESS  	read-write
	STATUS 	current
	DESCRIPTION 
		"The hysteresis used for voltage alarm deassertions in Volts(V)."
	::= { pduInputPhaseConfigEntry 15 }
	
pduInputPhaseConfigVoltageAlarmStateChangeDelay  OBJECT-TYPE
	SYNTAX 	Integer32
	MAX-ACCESS  	read-write
	STATUS 	current
	DESCRIPTION 
		"The delay measured in samples before a voltage state is asserted. If the 
		value is zero, then the state is asserted as soon as it is 
		detected; if it is non-zero, say n, then the assertion condition 
		must exist for n+1 consecutive samples before the corresponding 
		assertion event is reported. "
	::= { pduInputPhaseConfigEntry 16 }
	
pduInputPhaseConfigVoltageEnabledThresholds  OBJECT-TYPE
	SYNTAX 	BITS {
		lowerCritical (0),
		lowerWarning (1),
		upperWarning (2),
		upperCritical (3),
		disableall(4)
	}
	MAX-ACCESS  	read-write
	STATUS 	current
	DESCRIPTION 
		"A bit string indicating which voltage alarm thresholds are enabled."
	::= { pduInputPhaseConfigEntry 17 }
	
pduInputPhasePropertiesTable  OBJECT-TYPE
	SYNTAX SEQUENCE OF PduInputPhasePropertiesEntry
	MAX-ACCESS  	not-accessible
	STATUS 	current
	DESCRIPTION 
		"A table of PDU Input Phase properties"
	::= { pduInputPhase 3 }
	
pduInputPhasePropertiesEntry  OBJECT-TYPE
	SYNTAX 	PduInputPhasePropertiesEntry
	MAX-ACCESS  	not-accessible
	STATUS 	current
	DESCRIPTION 
		"An input phase properties entry containing objects for a particular input phase."
	INDEX { pduUnitPropertiesIndex, pduInputPhasePropertiesIndex }
	::= { pduInputPhasePropertiesTable 1 }

PduInputPhasePropertiesEntry ::= SEQUENCE {
	pduInputPhasePropertiesIndex
		Integer32,
	pduInputPhasePropertiesCount
		Integer32
	}

pduInputPhasePropertiesIndex  OBJECT-TYPE
	SYNTAX 	Integer32 (1..256)
	MAX-ACCESS  	not-accessible
	STATUS 	current
	DESCRIPTION 
		"The index of the PDU Input Phase STATUS entry"
	::= { pduInputPhasePropertiesEntry 1 }
	
pduInputPhasePropertiesCount  OBJECT-TYPE
	SYNTAX 	Integer32 (1..256)
	MAX-ACCESS  	read-only
	STATUS 	current
	DESCRIPTION 
		"The numeric Input Phase ID"
	::= { pduInputPhasePropertiesEntry 2 }
	
pduInputPhaseSTATUSTable  OBJECT-TYPE
	SYNTAX SEQUENCE OF PduInputPhaseSTATUSEntry
	MAX-ACCESS  	not-accessible
	STATUS 	current
	DESCRIPTION 
		"A table of PDU Input Phase STATUS data"
	::= { pduInputPhase 4 }
	
pduInputPhaseSTATUSEntry  OBJECT-TYPE
	SYNTAX 	PduInputPhaseSTATUSEntry
	MAX-ACCESS  	not-accessible
	STATUS 	current
	DESCRIPTION 
		"An input phase STATUS entry containing objects for a particular input phase."
	INDEX { pduUnitSTATUSIndex, pduInputPhaseSTATUSIndex }
	::= { pduInputPhaseSTATUSTable 1 }

PduInputPhaseSTATUSEntry ::= SEQUENCE {
	pduInputPhaseSTATUSIndex
		Integer32,
	pduInputPhaseSTATUSCount
		Integer32,
	pduInputPhaseSTATUSCurrentState
		INTEGER,
	pduInputPhaseSTATUSVoltageState
		INTEGER,
	pduInputPhaseSTATUSCurrent
		Integer32,
	pduInputPhaseSTATUSVoltage
		Integer32,
	pduInputPhaseSTATUSActivePower
		Integer32,
	pduInputPhaseSTATUSApparentPower
		Integer32,
	pduInputPhaseSTATUSPowerFactor
		Integer32
	}

pduInputPhaseSTATUSIndex  OBJECT-TYPE
	SYNTAX 	Integer32 (1..256)
	MAX-ACCESS  	not-accessible
	STATUS 	current
	DESCRIPTION 
		"The index of the PDU Input Phase STATUS entry"
	::= { pduInputPhaseSTATUSEntry 1 }
	
pduInputPhaseSTATUSCount  OBJECT-TYPE
	SYNTAX 	Integer32 (1..256)
	MAX-ACCESS  	read-only
	STATUS 	current
	DESCRIPTION 
		"The numeric Input Phase ID"
	::= { pduInputPhaseSTATUSEntry 2 }
	
pduInputPhaseSTATUSCurrentState  OBJECT-TYPE
	SYNTAX 	INTEGER {
		upperCritical (1),
		upperWarning (2),
		lowerWarning (3),
		lowerCritical (4),
		normal (5)
	}
	MAX-ACCESS  	read-only
	STATUS 	current
	DESCRIPTION 
		"Indicates the present current STATUS of the PDU Phase in case of Y connection or PDU Line in case of Delta conneciton."
	::= { pduInputPhaseSTATUSEntry 3 }
	
pduInputPhaseSTATUSVoltageState  OBJECT-TYPE
	SYNTAX 	INTEGER {
		upperCritical (1),
		upperWarning (2),
		lowerWarning (3),
		lowerCritical (4),
		normal (5)
	}
	MAX-ACCESS  	read-only
	STATUS 	current
	DESCRIPTION 
		"Indicates the present voltage STATUS of the PDU Input Phase being queried"
	::= { pduInputPhaseSTATUSEntry 4 }
	
pduInputPhaseSTATUSCurrent  OBJECT-TYPE
	SYNTAX 	Integer32
	MAX-ACCESS  	read-only
	STATUS 	current
	DESCRIPTION 
		"Returns the current draw, in hundredths of Amps(A)"
	::= { pduInputPhaseSTATUSEntry 5 }
	
pduInputPhaseSTATUSVoltage  OBJECT-TYPE
	SYNTAX 	Integer32
	MAX-ACCESS  	read-only
	STATUS 	current
	DESCRIPTION 
		"Returns the voltage, in Volts(V)"
	::= { pduInputPhaseSTATUSEntry 6 }
	
pduInputPhaseSTATUSActivePower  OBJECT-TYPE
	SYNTAX 	Integer32
	MAX-ACCESS  	read-only
	STATUS 	current
	DESCRIPTION 
		"Returns power consumption, in Watts(W)"
	::= { pduInputPhaseSTATUSEntry 7 }
	
pduInputPhaseSTATUSApparentPower  OBJECT-TYPE
	SYNTAX 	Integer32
	MAX-ACCESS  	read-only
	STATUS 	current
	DESCRIPTION 
		"Returns power consumption, in Volt-Amps(VA)"
	::= { pduInputPhaseSTATUSEntry 8 }
	
pduInputPhaseSTATUSPowerFactor  OBJECT-TYPE
	SYNTAX 	Integer32
	MAX-ACCESS  	read-only
	STATUS 	current
	DESCRIPTION 
		"Returns the ratio of active to apparent power of the PDU."
	::= { pduInputPhaseSTATUSEntry 9 }

-- Start pduCircuitBreaker
pduCircuitBreakerTableSize  OBJECT-TYPE
	SYNTAX 	Integer32 (1..256)
	MAX-ACCESS  	read-only
	STATUS 	current
	DESCRIPTION 
		"The number of PDU Circuit Breakers"
	::= { pduCircuitBreaker 1 }
	
pduCircuitBreakerConfigTable  OBJECT-TYPE
	SYNTAX SEQUENCE OF PduCircuitBreakerConfigEntry
	MAX-ACCESS  	not-accessible
	STATUS 	current
	DESCRIPTION 
		"A table of PDU Circuit Breaker configuration data"
	::= { pduCircuitBreaker 2 }
	
pduCircuitBreakerConfigEntry  OBJECT-TYPE
	SYNTAX 	PduCircuitBreakerConfigEntry
	MAX-ACCESS  	not-accessible
	STATUS 	current
	DESCRIPTION 
		"A circuit breaker configuration entry containing objects for a particular circuit breaker."
	INDEX { pduUnitConfigIndex, pduCircuitBreakerConfigIndex }
	::= { pduCircuitBreakerConfigTable 1 }

PduCircuitBreakerConfigEntry ::= SEQUENCE {
	pduCircuitBreakerConfigIndex
		Integer32,
	pduCircuitBreakerConfigCount
		Integer32,
	pduCircuitBreakerName
		DisplayString,
	pduCircuitBreakerConfigOverloadRestriction
		INTEGER,
	pduCircuitBreakerConfigLowerCriticalThreshold
		Unsigned32,
	pduCircuitBreakerConfigLowerWarningThreshold
		Unsigned32,
	pduCircuitBreakerConfigUpperCriticalThreshold
		Unsigned32,
	pduCircuitBreakerConfigUpperWarningThreshold
		Unsigned32,
	pduCircuitBreakerConfigAlarmResetThreshold
		Unsigned32,
	pduCircuitBreakerConfigAlarmStateChangeDelay
		Unsigned32,
	pduCircuitBreakerConfigEnabledThresholds
		BITS
	}

pduCircuitBreakerConfigIndex  OBJECT-TYPE
	SYNTAX 	Integer32 (1..256)
	MAX-ACCESS  	not-accessible
	STATUS 	current
	DESCRIPTION 
		"The index of the PDU Circuit Breaker configuration table entry"
	::= { pduCircuitBreakerConfigEntry 1 }
	
pduCircuitBreakerConfigCount  OBJECT-TYPE
	SYNTAX 	Integer32 (0..255)
	MAX-ACCESS  	read-only
	STATUS 	current
	DESCRIPTION 
		"The number of circuit breakers on the PDU"
	::= { pduCircuitBreakerConfigEntry 2 }
	
pduCircuitBreakerName  OBJECT-TYPE
	SYNTAX 	DisplayString
	MAX-ACCESS  	read-write
	STATUS 	current
	DESCRIPTION 
		"The label of the circuit breaker"
	::= { pduCircuitBreakerConfigEntry 3 }
	
pduCircuitBreakerConfigOverloadRestriction  OBJECT-TYPE
	SYNTAX 	INTEGER {
		alwaysAllowTurnOn (1),
		restrictOnUpperWarning (2),
		restrictOnUpperCritical (3),
		notSupported (4)
	}
	MAX-ACCESS  	read-write
	STATUS 	current
	DESCRIPTION 
		"This OID controls the behavior of a Switched PDU Circuit 
		Breaker when an overload condition is possible and additional 
		outlets are requested to be turned on. Setting this OID to 
		alwaysAllowTurnON (1) will always allow the outlets on the 
		corresponding Circuit Breaker to turn on. Setting this OID 
		to restrictOnUpperWarning (2) will not allow outlets on the 
		corresponding Circuit Breaker to turn on if the 
		pduCircuitBreakerConfigUpperWarningThreshold OID is exceeded. 
		Setting this OID to restrictOnUpperCritical (3) will not 
		allow outlets on the corresponding Circuit Breaker to turn 
		on if the pduCircuitBreakerConfigUpperCriticalThreshold OID 
		is exceeded. Models that do not support this feature will 
		respond to this OID with a value of notSupported (4). 
		Attempts to set this OID in these models will fail. "
	::= { pduCircuitBreakerConfigEntry 4 }

pduCircuitBreakerConfigLowerCriticalThreshold  OBJECT-TYPE
	SYNTAX 	Unsigned32
	MAX-ACCESS  	read-write
	STATUS 	current
	DESCRIPTION 
		"User-defined lower critical circuit breaker current alarm threshold in hundredths of Amps(A)."
	::= { pduCircuitBreakerConfigEntry 5 }
	
pduCircuitBreakerConfigLowerWarningThreshold  OBJECT-TYPE
	SYNTAX 	Unsigned32
	MAX-ACCESS  	read-write
	STATUS 	current
	DESCRIPTION 
		"User-defined lower non-critical (warning) circuit breaker current alarm threshold in hundredths of Amps(A)."
	::= { pduCircuitBreakerConfigEntry 6 }
	
pduCircuitBreakerConfigUpperCriticalThreshold  OBJECT-TYPE
	SYNTAX 	Unsigned32
	MAX-ACCESS  	read-write
	STATUS 	current
	DESCRIPTION 
		"User-defined upper critical circuit breaker current alarm threshold in hundredths of Amps(A)."
	::= { pduCircuitBreakerConfigEntry 7 }
	
pduCircuitBreakerConfigUpperWarningThreshold  OBJECT-TYPE
	SYNTAX 	Unsigned32
	MAX-ACCESS  	read-write
	STATUS 	current
	DESCRIPTION 
		"User-defined upper non-critical (warning) circuit breaker current alarm threshold in hundredths of Amps(A)."
	::= { pduCircuitBreakerConfigEntry 8 }
	
pduCircuitBreakerConfigAlarmResetThreshold  OBJECT-TYPE
	SYNTAX 	Unsigned32
	MAX-ACCESS  	read-write
	STATUS 	current
	DESCRIPTION 
		"The hysteresis used for deassertions in hundredths of Amps(A)."
	::= { pduCircuitBreakerConfigEntry 9 }
	
pduCircuitBreakerConfigAlarmStateChangeDelay  OBJECT-TYPE
	SYNTAX 	Unsigned32
	MAX-ACCESS  	read-write
	STATUS 	current
	DESCRIPTION 
		"The delay measured in samples before a state is asserted. 
		If the value is zero, then the state is asserted as soon 
		as it is detected; if it is non-zero, say n, then the 
		assertion condition must exist for n+1 consecutive samples 
		before the corresponding assertion event is reported."
	::= { pduCircuitBreakerConfigEntry 10 }
	
pduCircuitBreakerConfigEnabledThresholds  OBJECT-TYPE
	SYNTAX 	BITS {
		lowerCritical (0),
		lowerWarning (1),
		upperWarning (2),
		upperCritical (3),
		disableall (4)
	}
	MAX-ACCESS  	read-write
	STATUS 	current
	DESCRIPTION 
		"A bit string indicating which alarm thresholds are enabled."
	::= { pduCircuitBreakerConfigEntry 11 }

pduCircuitBreakerPropertiesTable  OBJECT-TYPE
	SYNTAX SEQUENCE OF PduCircuitBreakerPropertiesEntry
	MAX-ACCESS  	not-accessible
	STATUS 	current
	DESCRIPTION 
		"A table of PDU circuit breaker properties"
	::= { pduCircuitBreaker 3 }

pduCircuitBreakerPropertiesEntry  OBJECT-TYPE
	SYNTAX 	PduCircuitBreakerPropertiesEntry
	MAX-ACCESS  	not-accessible
	STATUS 	current
	DESCRIPTION 
		"A circuit breaker properties entry containing objects for a particular circuit breaker."
	INDEX { pduUnitPropertiesIndex, pduCircuitBreakerPropertiesIndex }
	::= { pduCircuitBreakerPropertiesTable 1 }

PduCircuitBreakerPropertiesEntry ::= SEQUENCE {
	pduCircuitBreakerPropertiesIndex
		Integer32,
	pduCircuitBreakerPropertiesCount
		Integer32,
	pduCircuitBreakerPropertiesInputLayout
		INTEGER,
	pduCircuitBreakerPropertiesCurrentRating
		Integer32
	}

pduCircuitBreakerPropertiesIndex  OBJECT-TYPE
	SYNTAX 	Integer32 (1..256)
	MAX-ACCESS  	not-accessible
	STATUS 	current
	DESCRIPTION 
		"The index of the PDU Circuit Breaker properties table entry"
	::= { pduCircuitBreakerPropertiesEntry 1 }
	
pduCircuitBreakerPropertiesCount  OBJECT-TYPE
	SYNTAX 	Integer32 (0..255)
	MAX-ACCESS  	read-only
	STATUS 	current
	DESCRIPTION 
		"The number of Circuit Breakers"
	::= { pduCircuitBreakerPropertiesEntry 2 }
	
pduCircuitBreakerPropertiesInputLayout  OBJECT-TYPE
	SYNTAX 	INTEGER {
		seqPhase1ToNeutral (1),
		seqPhase2ToNeutral (2),
		seqPhase3ToNeutral (3),
		seqPhase1ToPhase2 (4),
		seqPhase2ToPhase3 (5),
		seqPhase3ToPhase1 (6)
	}
	MAX-ACCESS  	read-only
	STATUS 	current
	DESCRIPTION 
		"This OID describes the outlet phase connections on 
		the referenced bank as follows: 
		seqPhase1ToNeutral(1) indicates that outlets attached 
		to circuit breaker are connected from Phase 1 to Neutral. 
		seqPhase2ToNeutral(2) indicates that outlets attached 
		to circuit breaker are connected from Phase 2 to Neutral. 
		seqPhase3ToNeutral(3) indicates that outlets attached 
		to circuit breaker are connected from Phase 3 to Neutral. 
		seqPhase1ToPhase2(4) indicates that outlets attached 
		to circuit breaker are connected from Phase 1 to Phase2. 
		seqPhase2ToPhase3(5) indicates that outlets attached 
		to circuit breaker are connected from Phase 2 to Phase3.  
		seqPhase3ToPhase1(6) indicates that outlets attached 
		to circuit breaker are connected from Phase 3 to Phase1. "
	::= { pduCircuitBreakerPropertiesEntry 3 }

pduCircuitBreakerPropertiesCurrentRating  OBJECT-TYPE
	SYNTAX 	Integer32 (0..255)
	MAX-ACCESS  	read-only
	STATUS 	current
	DESCRIPTION 
		"CircuitBreaker CurrentRating in hundreths of ampere"
	::= { pduCircuitBreakerPropertiesEntry 4 }

pduCircuitBreakerSTATUSTable  OBJECT-TYPE
	SYNTAX SEQUENCE OF PduCircuitBreakerSTATUSEntry
	MAX-ACCESS  	not-accessible
	STATUS 	current
	DESCRIPTION 
		"A table of PDU circuit breaker STATUS data"
	::= { pduCircuitBreaker 4 }
	
pduCircuitBreakerSTATUSEntry  OBJECT-TYPE
	SYNTAX 	PduCircuitBreakerSTATUSEntry
	MAX-ACCESS  	not-accessible
	STATUS 	current
	DESCRIPTION 
		"A circuit breaker STATUS entry containing objects for a particular circuit breaker."
	INDEX { pduUnitSTATUSIndex, pduCircuitBreakerSTATUSIndex }
	::= { pduCircuitBreakerSTATUSTable 1 }

PduCircuitBreakerSTATUSEntry ::= SEQUENCE {
	pduCircuitBreakerSTATUSIndex
		Integer32,
	pduCircuitBreakerSTATUSCount
		Integer32,
	pduCircuitBreakerLabel
		DisplayString,
	pduCircuitBreakerSTATUSLoadState
		INTEGER,
	pduCircuitBreakerSTATUSCurrent
		Integer32,
	pduCircuitBreakerSTATUSPowerFactor
		Integer32
	}

pduCircuitBreakerSTATUSIndex  OBJECT-TYPE
	SYNTAX 	Integer32 (1..256)
	MAX-ACCESS  	not-accessible
	STATUS 	current
	DESCRIPTION 
		"The index of the PDU Circuit Breaker STATUS table entry"
	::= { pduCircuitBreakerSTATUSEntry 1 }
	
pduCircuitBreakerSTATUSCount  OBJECT-TYPE
	SYNTAX 	Integer32 (0..255)
	MAX-ACCESS  	read-only
	STATUS 	current
	DESCRIPTION 
		"The number of Circuit Breakers"
	::= { pduCircuitBreakerSTATUSEntry 2 }
	
pduCircuitBreakerLabel  OBJECT-TYPE
	SYNTAX 	DisplayString
	MAX-ACCESS  	read-only
	STATUS 	current
	DESCRIPTION 
		"The label on the PDU identifying the circuit breaker"
	::= { pduCircuitBreakerSTATUSEntry 3 }
	
pduCircuitBreakerSTATUSLoadState  OBJECT-TYPE
	SYNTAX 	INTEGER {
		upperCritical (1),
		upperWarning (2),
		lowerWarning (3),
		lowerCritical (4),
		normal (5),
		off (6)
	}
	MAX-ACCESS  	read-only
	STATUS 	current
	DESCRIPTION 
		"Indicates the present load STATUS of the PDU Circuit 
		Breaker being queried"
	::= { pduCircuitBreakerSTATUSEntry 4 }
	
pduCircuitBreakerSTATUSCurrent  OBJECT-TYPE
	SYNTAX 	Integer32
	MAX-ACCESS  	read-only
	STATUS 	current
	DESCRIPTION 
		"Returns the current draw, in hundredths of Amps(A), of the load on 
		the PDU Circuit Breaker being queried."
	::= { pduCircuitBreakerSTATUSEntry 5 }
	
pduCircuitBreakerSTATUSPowerFactor  OBJECT-TYPE
	SYNTAX 	Integer32
	MAX-ACCESS  	read-only
	STATUS 	current
	DESCRIPTION 
		"Displays the CB Power Factor (ratio of active power to apparent power) in hundredths.
		Example: Power Factor=1, pduCircuitBreakerSTATUSPowerFactor displays as 100"
	::= { pduCircuitBreakerSTATUSEntry 6 }
	
-- Start pduOutlet
pduOutletSwitchedTableSize  OBJECT-TYPE
	SYNTAX 	Integer32 (1..256)
	MAX-ACCESS  	read-only
	STATUS 	current
	DESCRIPTION 
		"The number of PDU Outlets"
	::= { pduOutlet 1 }

pduOutletSwitchedConfigTable  OBJECT-TYPE
	SYNTAX SEQUENCE OF PduOutletSwitchedConfigEntry
	MAX-ACCESS  	not-accessible
	STATUS 	current
	DESCRIPTION 
		"A table of PDU Switched Outlet configuration data"
	::= { pduOutlet 2 }
	
pduOutletSwitchedConfigEntry  OBJECT-TYPE
	SYNTAX 	PduOutletSwitchedConfigEntry
	MAX-ACCESS  	not-accessible
	STATUS 	current
	DESCRIPTION 
		"An outlet configuration entry containing objects for a particular outlet."
	INDEX { pduUnitConfigIndex, pduOutletSwitchedConfigIndex }
	::= { pduOutletSwitchedConfigTable 1 }

PduOutletSwitchedConfigEntry ::= SEQUENCE {
	pduOutletSwitchedConfigIndex
		Integer32,
	pduOutletSwitchedName
		DisplayString,
	pduOutletSwitchedStateOnStartup
		INTEGER,
	pduOutletSwitchedConfigPowerOnTime
		Integer32,
	pduOutletSwitchedConfigPowerOffTime
		Integer32,
	pduOutletSwitchedConfigRebootDuration
		Integer32
	}

pduOutletSwitchedConfigIndex  OBJECT-TYPE
	SYNTAX 	Integer32 (1..256)
	MAX-ACCESS  	not-accessible
	STATUS 	current
	DESCRIPTION 
		"The index of the PDU Switched Outlet configuration table entry"
	::= { pduOutletSwitchedConfigEntry 1 }

pduOutletSwitchedName  OBJECT-TYPE
	SYNTAX 	DisplayString
	MAX-ACCESS  	read-write
	STATUS 	current
	DESCRIPTION 
		"The user-defined name for the Switched Outlet"
	::= { pduOutletSwitchedConfigEntry 2 }

pduOutletSwitchedStateOnStartup  OBJECT-TYPE
	SYNTAX 	INTEGER {
		off (0),
		on (1),
		lastKnownState (2)
		}
	MAX-ACCESS  	read-write
	STATUS 	current
	DESCRIPTION 
		"The outlet state on device startup; overrides 
		the global value pduUnitConfigGlobalOutletStateOnStartup."
	::= { pduOutletSwitchedConfigEntry 3 }

pduOutletSwitchedConfigPowerOnTime  OBJECT-TYPE
	SYNTAX 	Integer32
	MAX-ACCESS  	read-write
	STATUS 	current
	DESCRIPTION 
		"The amount of delay, in seconds, between when power is 
		provided to outlets the outlet and when this outlet 
		starts providing power"
	::= { pduOutletSwitchedConfigEntry 4 }

pduOutletSwitchedConfigPowerOffTime  OBJECT-TYPE
	SYNTAX 	Integer32
	MAX-ACCESS  	read-write
	STATUS 	current
	DESCRIPTION 
		"The amount of time, in seconds, this outlet will delay 
		powering off"
	::= { pduOutletSwitchedConfigEntry 5 }

pduOutletSwitchedConfigRebootDuration  OBJECT-TYPE
	SYNTAX 	Integer32
	MAX-ACCESS  	read-write
	STATUS 	current
	DESCRIPTION 
		"The amount of time, in seconds, this outlet will remain 
		in powered off state before returning to power on state 
		during a reboot action."
	::= { pduOutletSwitchedConfigEntry 6 }
	
pduOutletSwitchedPropertiesTable  OBJECT-TYPE
	SYNTAX SEQUENCE OF PduOutletSwitchedPropertiesEntry
	MAX-ACCESS  	not-accessible
	STATUS 	current
	DESCRIPTION 
		"A table of PDU Switched Outlet properties"
	::= { pduOutlet 3 }
	
pduOutletSwitchedPropertiesEntry  OBJECT-TYPE
	SYNTAX 	PduOutletSwitchedPropertiesEntry
	MAX-ACCESS  	not-accessible
	STATUS 	current
	DESCRIPTION 
		"An outlet properties entry containing objects for a particular outlet."
	INDEX { pduUnitPropertiesIndex, pduOutletSwitchedPropertiesIndex }
	::= { pduOutletSwitchedPropertiesTable 1 }

PduOutletSwitchedPropertiesEntry ::= SEQUENCE {
	pduOutletSwitchedPropertiesIndex
		Integer32,
	pduOutletSwitchedPropertiesNumber
		Integer32,
	pduOutletSwitchedPropertiesName
		DisplayString,
	pduOutletSwitchedPropertiesInputPhaseLayout
		INTEGER,
	pduOutletSwitchedPropertiesCircuitBreaker
		Integer32,
	pduOutletSwitchedPropertiesCurrentRating
		Integer32
	}

pduOutletSwitchedPropertiesIndex  OBJECT-TYPE
	SYNTAX 	Integer32 (1..256)
	MAX-ACCESS  	not-accessible
	STATUS 	current
	DESCRIPTION 
		"The index of the PDU Switched Outlet properties table entry"
	::= { pduOutletSwitchedPropertiesEntry 1 }

pduOutletSwitchedPropertiesNumber  OBJECT-TYPE
	SYNTAX 	Integer32 (1..256)
	MAX-ACCESS  	read-only
	STATUS 	current
	DESCRIPTION 
		"The numeric Switched Outlet ID"
	::= { pduOutletSwitchedPropertiesEntry 2 }

pduOutletSwitchedPropertiesName  OBJECT-TYPE
	SYNTAX 	DisplayString
	MAX-ACCESS  	read-only
	STATUS 	current
	DESCRIPTION 
		"The user-defined switched outlet ID string"
	::= { pduOutletSwitchedPropertiesEntry 3 }
	
pduOutletSwitchedPropertiesInputPhaseLayout  OBJECT-TYPE
	SYNTAX 	INTEGER {
		seqPhase1ToNeutral (1),
		seqPhase2ToNeutral (2),
		seqPhase3ToNeutral (3),
		seqPhase1ToPhase2 (4),
		seqPhase2ToPhase3 (5),
		seqPhase3ToPhase1 (6)
	}
	MAX-ACCESS  	read-only
	STATUS 	current
	DESCRIPTION 
		"This OID describes the outlet phase connections 
		on the referenced bank as follows: 
		seqPhase1ToNeutral(1) indicates that outlets 
		attached to Switched Outlet are connected from Phase 1 to Neutral. 
		seqPhase2ToNeutral(2) indicates that outlets 
		attached to Switched Outlet are connected from Phase 2 to Neutral. 
		seqPhase3ToNeutral(3) indicates that outlets 
		attached to Switched Outlet are connected from Phase 3 to Neutral. 
		seqPhase1ToPhase2(4) indicates that outlets 
		attached to Switched Outlet are connected from Phase 1 to Phase2. 
		seqPhase2ToPhase3(5) indicates that outlets 
		attached to Switched Outlet are connected from Phase 2 to Phase3.  
		seqPhase3ToPhase1(6) indicates that outlets 
		attached to Switched Outlet are connected from Phase 3 to Phase1. "
	::= { pduOutletSwitchedPropertiesEntry 4 }

pduOutletSwitchedPropertiesCircuitBreaker  OBJECT-TYPE
	SYNTAX 	Integer32 (1..256)
	MAX-ACCESS  	read-only
	STATUS 	current
	DESCRIPTION 
		"The numeric Circuit Breaker ID"
	::= { pduOutletSwitchedPropertiesEntry 5 }
	
pduOutletSwitchedPropertiesCurrentRating  OBJECT-TYPE
	SYNTAX 	Integer32 (1..256)
	MAX-ACCESS  	read-only
	STATUS 	current
	DESCRIPTION 
		"The current rating of outlet in hundreths of ampere"
	::= { pduOutletSwitchedPropertiesEntry 6 }

pduOutletSwitchedSTATUSTable  OBJECT-TYPE
	SYNTAX SEQUENCE OF PduOutletSwitchedSTATUSEntry
	MAX-ACCESS  	not-accessible
	STATUS 	current
	DESCRIPTION 
		"A table of PDU Switched Outlet STATUS data"
	::= { pduOutlet 4 }

pduOutletSwitchedSTATUSEntry  OBJECT-TYPE
	SYNTAX 	PduOutletSwitchedSTATUSEntry
	MAX-ACCESS  	not-accessible
	STATUS 	current
	DESCRIPTION 
		"STATUS data from the PDU Switched Outlet being queried"
	INDEX { pduUnitSTATUSIndex, pduOutletSwitchedSTATUSIndex }
	::= { pduOutletSwitchedSTATUSTable 1 }

PduOutletSwitchedSTATUSEntry ::= SEQUENCE {
	pduOutletSwitchedSTATUSIndex
		Integer32,
	pduOutletSwitchedSTATUSNumber
		Integer32,
	pduOutletSwitchedSTATUSName
		DisplayString,
	pduOutletSwitchedSTATUSState
		INTEGER
	}

pduOutletSwitchedSTATUSIndex  OBJECT-TYPE
	SYNTAX 	Integer32 (1..256)
	MAX-ACCESS  	not-accessible
	STATUS 	current
	DESCRIPTION 
		"The index of the PDU Switched Outlet STATUS table entry"
	::= { pduOutletSwitchedSTATUSEntry 1 }

pduOutletSwitchedSTATUSNumber  OBJECT-TYPE
	SYNTAX 	Integer32 (1..256)
	MAX-ACCESS  	read-only
	STATUS 	current
	DESCRIPTION 
		"The numeric Switched Outlet ID"
	::= { pduOutletSwitchedSTATUSEntry 2 }

pduOutletSwitchedSTATUSName  OBJECT-TYPE
	SYNTAX 	DisplayString
	MAX-ACCESS  	read-only
	STATUS 	current
	DESCRIPTION 
		"The user-defined switched outlet ID string"
	::= { pduOutletSwitchedSTATUSEntry 3 }

pduOutletSwitchedSTATUSState  OBJECT-TYPE
	SYNTAX 	INTEGER {
		off (0),
		on (1)
	}
	MAX-ACCESS  	read-only
	STATUS 	current
	DESCRIPTION 
		"Indicates the present switch state of the 
		PDU switched outlet being queried"
	::= { pduOutletSwitchedSTATUSEntry 4 }
	
pduOutletSwitchedControlTable  OBJECT-TYPE
	SYNTAX SEQUENCE OF PduOutletSwitchedControlEntry
	MAX-ACCESS  	not-accessible
	STATUS 	current
	DESCRIPTION 
		"A table of PDU Switched Outlet STATUS data"
	::= { pduOutlet 5 }
	
pduOutletSwitchedControlEntry  OBJECT-TYPE
	SYNTAX 	PduOutletSwitchedControlEntry
	MAX-ACCESS  	not-accessible
	STATUS 	current
	DESCRIPTION 
		"STATUS data from the PDU Switched Outlet 
		being queried"
	INDEX { pduUnitConfigIndex, pduOutletSwitchedControlIndex }
	::= { pduOutletSwitchedControlTable 1 }

PduOutletSwitchedControlEntry ::= SEQUENCE {
	pduOutletSwitchedControlIndex
		Integer32,
	pduOutletSwitchedControlNumber
		Integer32,
	pduOutletSwitchedControlName
		DisplayString,
	pduOutletSwitchedControlCommand
		INTEGER
	}

pduOutletSwitchedControlIndex  OBJECT-TYPE
	SYNTAX 	Integer32 (1..256)
	MAX-ACCESS  	not-accessible
	STATUS 	current
	DESCRIPTION 
		"The index to the PDU switched outlet 
		control data table entry"
	::= { pduOutletSwitchedControlEntry 1 }
	
pduOutletSwitchedControlNumber  OBJECT-TYPE
	SYNTAX 	Integer32 (1..256)
	MAX-ACCESS  	read-only
	STATUS 	current
	DESCRIPTION 
		"The numeric Switched Outlet ID"
	::= { pduOutletSwitchedControlEntry 2 }
	
pduOutletSwitchedControlName  OBJECT-TYPE
	SYNTAX 	DisplayString
	MAX-ACCESS  	read-only
	STATUS 	current
	DESCRIPTION 
		"The user-defined switched outlet ID string"
	::= { pduOutletSwitchedControlEntry 3 }

pduOutletSwitchedControlCommand  OBJECT-TYPE
	SYNTAX 	INTEGER {
		immediateOff (1),
		immediateOn (2),
		delayedOff (3),
		delayedOn (4),
		immediateReboot (5),
		delayedReboot (6),
		outletUnknown (7)
		}
	MAX-ACCESS  	read-write
	STATUS 	current
	DESCRIPTION 
		"Getting this variable will return the outlet state.
		If the outlet is on, the immediateOn (2) 
		value will be returned. If the outlet is off, 
		the immediateOff (1) value will be returned. 
		If the state of the outlet cannot be determined, the 
		outletUnknown (7) value will be returned. If the 
		outletUnknown condition should occur, all devices 
		powered by the PDU should be shut down. The PDU's 
		power should then be cycled to clear this condition. 
		Setting this variable to immediateOn (2) will immediately 
		turn the outlet on. Setting this variable to 
		immediateOff (1) will immediately turn the outlet off. 
		Setting this variable to immediateReboot (5) 
		will cause the Switched PDU to perform an immediateOff 
		command, wait the pduOutletSwitchedConfigRebootDuration 
		OID time, and then perform an immediateOn command.
		Setting this variable to delayedOn (4) will turn the 
		outlet on after the pduOutletSwitchedConfigPowerOnTime 
		OID time has elapsed. Setting this variable to 
		delayedOff (3) will turn the outlet off after the 
		pduOutletSwitchedConfigPowerOffTime OID time has elapsed. 
		Setting this variable to delayedReboot  (6) will cause 
		the Switched PDU to perform a delayedOff command, wait 
		the pduOutletSwitchedConfigRebootDuration OID time, and 
		then perform a delayedOn command."
	::= { pduOutletSwitchedControlEntry 4 }

pduOutletMeteredTableSize  OBJECT-TYPE
	SYNTAX 	Integer32 (1..256)
	MAX-ACCESS  	read-only
	STATUS 	current
	DESCRIPTION 
		"The number of PDU Outlets"
	::= { pduOutlet 6 }

pduOutletMeteredConfigTable  OBJECT-TYPE
	SYNTAX SEQUENCE OF PduOutletMeteredConfigEntry
	MAX-ACCESS  	not-accessible
	STATUS 	current
	DESCRIPTION 
		"A table of PDU Metered Outlet configuration data"
	::= { pduOutlet 7 }

pduOutletMeteredConfigEntry  OBJECT-TYPE
	SYNTAX 	PduOutletMeteredConfigEntry
	MAX-ACCESS  	not-accessible
	STATUS 	current
	DESCRIPTION 
		"An outlet configuration entry containing objects for a particular outlet."
	INDEX { pduUnitConfigIndex, pduOutletMeteredConfigIndex }
	::= { pduOutletMeteredConfigTable 1 }

PduOutletMeteredConfigEntry ::= SEQUENCE {
	pduOutletMeteredConfigIndex
		Integer32,
	pduOutletMeteredName
		DisplayString,
	pduOutletMeteredConfigLowerCriticalThreshold
		Unsigned32,
	pduOutletMeteredConfigLowerWarningThreshold
		Unsigned32,
	pduOutletMeteredConfigUpperCriticalThreshold
		Unsigned32,
	pduOutletMeteredConfigUpperWarningThreshold
		Unsigned32,
	pduOutletMeteredConfigAlarmResetThreshold
		Unsigned32,
	pduOutletMeteredConfigAlarmStateChangeDelay
		Unsigned32,
	pduOutletMeteredConfigEnabledThresholds
		BITS
	}

pduOutletMeteredConfigIndex  OBJECT-TYPE
	SYNTAX 	Integer32 (1..256)
	MAX-ACCESS  	not-accessible
	STATUS 	current
	DESCRIPTION 
		"The index of the PDU Metered Outlet 
		configuration table entry"
	::= { pduOutletMeteredConfigEntry 1 }

pduOutletMeteredName  OBJECT-TYPE
	SYNTAX 	DisplayString
	MAX-ACCESS  	read-write
	STATUS 	current
	DESCRIPTION 
		"The user-defined name for the Metered Outlet"
	::= { pduOutletMeteredConfigEntry 2 }

pduOutletMeteredConfigLowerCriticalThreshold  OBJECT-TYPE
	SYNTAX 	Unsigned32
	MAX-ACCESS  	read-write
	STATUS 	current
	DESCRIPTION 
		"User-defined lower critical outlet active power alarm threshold in Watts(W)."
	::= { pduOutletMeteredConfigEntry 3 }

pduOutletMeteredConfigLowerWarningThreshold  OBJECT-TYPE
	SYNTAX 	Unsigned32
	MAX-ACCESS  	read-write
	STATUS 	current
	DESCRIPTION 
		"User-defined lower non-critical (warning) outlet active power alarm threshold in Watts(W)."
	::= { pduOutletMeteredConfigEntry 4 }

pduOutletMeteredConfigUpperCriticalThreshold  OBJECT-TYPE
	SYNTAX 	Unsigned32
	MAX-ACCESS  	read-write
	STATUS 	current
	DESCRIPTION 
		"User-defined upper critical outlet active power alarm threshold in Watts(W)."
	::= { pduOutletMeteredConfigEntry 5 }

pduOutletMeteredConfigUpperWarningThreshold  OBJECT-TYPE
	SYNTAX 	Unsigned32
	MAX-ACCESS  	read-write
	STATUS 	current
	DESCRIPTION 
		"User-defined upper non-critical (warning) outlet active power alarm threshold in Watts(W)."
	::= { pduOutletMeteredConfigEntry 6 }

pduOutletMeteredConfigAlarmResetThreshold  OBJECT-TYPE
	SYNTAX 	Unsigned32
	MAX-ACCESS  	read-write
	STATUS 	current
	DESCRIPTION 
		"The hysteresis used for deassertions in Watts(W)."
	::= { pduOutletMeteredConfigEntry 7 }

pduOutletMeteredConfigAlarmStateChangeDelay  OBJECT-TYPE
	SYNTAX 	Unsigned32
	MAX-ACCESS  	read-write
	STATUS 	current
	DESCRIPTION 
		"The delay measured in samples before a state 
		is asserted. If the value is zero, then the state 
		is asserted as soon as it is detected; if it is 
		non-zero, say n, then the assertion condition must 
		exist for n+1 consecutive samples before the 
		corresponding assertion event is reported."
	::= { pduOutletMeteredConfigEntry 8 }

pduOutletMeteredConfigEnabledThresholds  OBJECT-TYPE
	SYNTAX 	BITS {
		lowerCritical (0),
		lowerWarning (1),
		upperWarning (2),
		upperCritical (3),
		disableall (4)
	}
	MAX-ACCESS  	read-write
	STATUS 	current
	DESCRIPTION 
		"A bit string indicating which alarm 
		thresholds are enabled."
	::= { pduOutletMeteredConfigEntry 9 }

pduOutletMeteredPropertiesTable  OBJECT-TYPE
	SYNTAX SEQUENCE OF PduOutletMeteredPropertiesEntry
	MAX-ACCESS  	not-accessible
	STATUS 	current
	DESCRIPTION 
		"A table of PDU Metered Outlet properties"
	::= { pduOutlet 8 }

pduOutletMeteredPropertiesEntry  OBJECT-TYPE
	SYNTAX 	PduOutletMeteredPropertiesEntry
	MAX-ACCESS  	not-accessible
	STATUS 	current
	DESCRIPTION 
		"Configuration data from the PDU Metered 
		Outlet being queried"
	INDEX { pduUnitPropertiesIndex, pduOutletMeteredPropertiesIndex }
	::= { pduOutletMeteredPropertiesTable 1 }

PduOutletMeteredPropertiesEntry ::= SEQUENCE {
	pduOutletMeteredPropertiesIndex
		Integer32,
	pduOutletMeteredPropertiesNumber
		Integer32,
	pduOutletMeteredPropertiesName
		DisplayString,
	pduOutletMeteredPropertiesInputPhaseLayout
		INTEGER,
	pduOutletMeteredPropertiesCircuitBreaker
		Integer32,
	pduOutletMeteredPropertiesPowerRating
		Integer32,
	pduOutletMeteredPropertiesCurrentRating
		Integer32
	}

pduOutletMeteredPropertiesIndex  OBJECT-TYPE
	SYNTAX 	Integer32 (1..256)
	MAX-ACCESS  	not-accessible
	STATUS 	current
	DESCRIPTION 
		"The index of the PDU Metered Outlet 
		properties table entry"
	::= { pduOutletMeteredPropertiesEntry 1 }

pduOutletMeteredPropertiesNumber  OBJECT-TYPE
	SYNTAX 	Integer32 (1..256)
	MAX-ACCESS  	read-only
	STATUS 	current
	DESCRIPTION 
		"The numeric Metered Outlet ID"
	::= { pduOutletMeteredPropertiesEntry 2 }

pduOutletMeteredPropertiesName  OBJECT-TYPE
	SYNTAX 	DisplayString
	MAX-ACCESS  	read-only
	STATUS 	current
	DESCRIPTION 
		"The user-defined Metered outlet ID string"
	::= { pduOutletMeteredPropertiesEntry 3 }

pduOutletMeteredPropertiesInputPhaseLayout  OBJECT-TYPE
	SYNTAX 	INTEGER {
		seqPhase1ToNeutral (1),
		seqPhase2ToNeutral (2),
		seqPhase3ToNeutral (3),
		seqPhase1ToPhase2 (4),
		seqPhase2ToPhase3 (5),
		seqPhase3ToPhase1 (6)
	}
	MAX-ACCESS  	read-only
	STATUS 	current
	DESCRIPTION 
		"This OID describes the outlet phase connections 
		on the referenced bank as follows: 
		seqPhase1ToNeutral(1) indicates that outlets attached 
		to Metered Outlet are connected from Phase 1 to Neutral. 
		seqPhase2ToNeutral(2) indicates that outlets attached 
		to Metered Outlet are connected from Phase 2 to Neutral. 
		seqPhase3ToNeutral(3) indicates that outlets attached 
		to Metered Outlet are connected from Phase 3 to Neutral. 
		seqPhase1ToPhase2(4) indicates that outlets attached 
		to Metered Outlet are connected from Phase 1 to Phase2. 
		seqPhase2ToPhase3(5) indicates that outlets attached 
		to Metered Outlet are connected from Phase 2 to Phase3.  
		seqPhase3ToPhase1(6) indicates that outlets attached 
		to Metered Outlet are connected from Phase 3 to Phase1. "
	::= { pduOutletMeteredPropertiesEntry 4 }

pduOutletMeteredPropertiesCircuitBreaker  OBJECT-TYPE
	SYNTAX 	Integer32 (1..256)
	MAX-ACCESS  	read-only
	STATUS 	current
	DESCRIPTION 
		"The numeric Circuit Breaker ID"
	::= { pduOutletMeteredPropertiesEntry 5 }

pduOutletMeteredPropertiesPowerRating  OBJECT-TYPE
	SYNTAX 	Integer32
	MAX-ACCESS  	read-only
	STATUS 	current
	DESCRIPTION 
		"Maximum power rating of the PDU metered outlet"
	::= { pduOutletMeteredPropertiesEntry 6 }

pduOutletMeteredPropertiesCurrentRating  OBJECT-TYPE
	SYNTAX 	Integer32
	MAX-ACCESS  	read-only
	STATUS 	current
	DESCRIPTION 
		"Metered outlet current rating in hundreths of ampere"
	::= { pduOutletMeteredPropertiesEntry 7 }
	
pduOutletMeteredSTATUSTable  OBJECT-TYPE
	SYNTAX SEQUENCE OF PduOutletMeteredSTATUSEntry
	MAX-ACCESS  	not-accessible
	STATUS 	current
	DESCRIPTION 
		"A table of PDU Metered Outlet STATUS data"
	::= { pduOutlet 9 }
	
pduOutletMeteredSTATUSEntry  OBJECT-TYPE
	SYNTAX 	PduOutletMeteredSTATUSEntry
	MAX-ACCESS  	not-accessible
	STATUS 	current
	DESCRIPTION 
		"STATUS data from the PDU Metered Outlet being queried"
	INDEX { pduUnitSTATUSIndex, pduOutletMeteredSTATUSIndex }
	::= { pduOutletMeteredSTATUSTable 1 }

PduOutletMeteredSTATUSEntry ::= SEQUENCE {
	pduOutletMeteredSTATUSIndex
		Integer32,
	pduOutletMeteredSTATUSNumber
		Integer32,
	pduOutletMeteredSTATUSName
		DisplayString,
	pduOutletMeteredSTATUSLoadState
		INTEGER,
	pduOutletMeteredSTATUSCurrent
		Integer32,
	pduOutletMeteredSTATUSActivePower
		Integer32,
	pduOutletMeteredSTATUSPowerFactor
		Integer32,
	pduOutletMeteredSTATUSPeakPower
		Integer32,
	pduOutletMeteredSTATUSPeakPowerTimeStamp
		DisplayString,
	pduOutletMeteredSTATUSPeakPowerStartTime
		DisplayString,
	pduOutletMeteredSTATUSResettableEnergy
		Integer32
	}

pduOutletMeteredSTATUSIndex  OBJECT-TYPE
	SYNTAX 	Integer32 (1..256)
	MAX-ACCESS  	not-accessible
	STATUS 	current
	DESCRIPTION 
		"The index of the PDU Metered Outlet STATUS table entry"
	::= { pduOutletMeteredSTATUSEntry 1 }

pduOutletMeteredSTATUSNumber  OBJECT-TYPE
	SYNTAX 	Integer32 (1..256)
	MAX-ACCESS  	read-only
	STATUS 	current
	DESCRIPTION 
		"The numeric Metered Outlet ID"
	::= { pduOutletMeteredSTATUSEntry 2 }

pduOutletMeteredSTATUSName  OBJECT-TYPE
	SYNTAX 	DisplayString
	MAX-ACCESS  	read-only
	STATUS 	current
	DESCRIPTION 
		"The user-defined Metered outlet ID string"
	::= { pduOutletMeteredSTATUSEntry 3 }
	
pduOutletMeteredSTATUSLoadState  OBJECT-TYPE
	SYNTAX 	INTEGER {
		upperCritical (1),
		upperWarning (2),
		lowerWarning (3),
		lowerCritical (4),
		normal (5)
	}
	MAX-ACCESS  	read-only
	STATUS 	current
	DESCRIPTION 
		"Returns the present load STATUS of the PDU metered outlet being queried."
	::= { pduOutletMeteredSTATUSEntry 4 }

pduOutletMeteredSTATUSCurrent  OBJECT-TYPE
	SYNTAX 	Integer32
	MAX-ACCESS  	read-only
	STATUS 	current
	DESCRIPTION 
		"Returns the current draw, in hundredths of Amps(A), of the load on the PDU 
		outlet being queried."
	::= { pduOutletMeteredSTATUSEntry 5 }

pduOutletMeteredSTATUSActivePower  OBJECT-TYPE
	SYNTAX 	Integer32
	MAX-ACCESS  	read-only
	STATUS 	current
	DESCRIPTION 
		"Returns the power draw, in Watts(W), of the load 
		on the PDU outlet being queried."
	::= { pduOutletMeteredSTATUSEntry 6 }
	
pduOutletMeteredSTATUSPowerFactor  OBJECT-TYPE
	SYNTAX 	Integer32
	MAX-ACCESS  	read-only
	STATUS 	current
	DESCRIPTION 
		"Returns the ratio of active to apparent power 
		of the PDU Outlet being queried"
	::= { pduOutletMeteredSTATUSEntry 7 }

pduOutletMeteredSTATUSPeakPower  OBJECT-TYPE
	SYNTAX 	Integer32
	MAX-ACCESS  	read-only
	STATUS 	current
	DESCRIPTION 
		"Returns peak power consumption, in Watts(W), 
		of the Rack PDU outlet being queried."
	::= { pduOutletMeteredSTATUSEntry 8 }

pduOutletMeteredSTATUSPeakPowerTimeStamp  OBJECT-TYPE
	SYNTAX 	DisplayString
	MAX-ACCESS  	read-only
	STATUS 	current
	DESCRIPTION 
		"Indicates the date and time that this metered 
		outlet's peak power consumption occurred"
	::= { pduOutletMeteredSTATUSEntry 9 }

pduOutletMeteredSTATUSPeakPowerStartTime  OBJECT-TYPE
	SYNTAX 	DisplayString
	MAX-ACCESS  	read-only
	STATUS 	current
	DESCRIPTION 
		"Indicates the start date and time that this metered 
		outlet began recording peak power observations"
	::= { pduOutletMeteredSTATUSEntry 10 }

pduOutletMeteredSTATUSResettableEnergy  OBJECT-TYPE
	SYNTAX 	Integer32
	MAX-ACCESS  	read-only
	STATUS 	current
	DESCRIPTION 
		"A user resettable energy meter measuring outlet load energy 
		consumption in tenths of Kilowatt-Hours(kWh)."
	::= { pduOutletMeteredSTATUSEntry 11 }

-- Start pduExternalSensor
pduExternalSensorTableSize  OBJECT-TYPE
	SYNTAX 	Integer32 (1..256)
	MAX-ACCESS  	read-only
	STATUS 	current
	DESCRIPTION 
		"The total number of External Sensors"
	::= { pduExternalSensor 1 }

pduExternalSensorNamePlateTable  OBJECT-TYPE
	SYNTAX SEQUENCE OF PduExternalSensorNamePlateEntry
	MAX-ACCESS  	not-accessible
	STATUS 	current
	DESCRIPTION 
		"A table of PDU ExternalSensorNamePlate data"
	::= { pduExternalSensor 2 }

pduExternalSensorNamePlateEntry  OBJECT-TYPE
	SYNTAX 	PduExternalSensorNamePlateEntry
	MAX-ACCESS  	not-accessible
	STATUS 	current
	DESCRIPTION 
		"External Sensor Name Plate data from the external 
		sensor being queried. The number of entries equals 
		the value of pduExternalSensorNamePlateTableSize."
	INDEX { pduNamePlateIndex, pduExternalSensorNamePlateIndex }
	::= { pduExternalSensorNamePlateTable 1 }

PduExternalSensorNamePlateEntry ::= SEQUENCE {
	pduExternalSensorNamePlateIndex
		Integer32,
	pduExternalSensorNamePlateName
		DisplayString,
	pduExternalSensorNamePlateDescription
		DisplayString,
	pduExternalSensorNamePlateLocation
		DisplayString,
	pduExternalSensorNamePlateSerialNumber
		DisplayString,
	pduExternalSensorNamePlateType
		INTEGER,
	pduExternalSensorNamePlateUnits
		INTEGER,
	pduExternalSensorNamePlateIdentifier
		Integer32
	}

pduExternalSensorNamePlateIndex  OBJECT-TYPE
	SYNTAX 	Integer32 (0..255)
	MAX-ACCESS  	not-accessible
	STATUS 	current
	DESCRIPTION 
		"The index of the PDU External Sensor STATUS table entry"
	::= { pduExternalSensorNamePlateEntry 1 }

pduExternalSensorNamePlateName  OBJECT-TYPE
	SYNTAX 	DisplayString
	MAX-ACCESS  	read-write
	STATUS 	current
	DESCRIPTION 
		"A user-defined string identifying the external sensor"
	::= { pduExternalSensorNamePlateEntry 2 }

pduExternalSensorNamePlateDescription  OBJECT-TYPE
	SYNTAX 	DisplayString
	MAX-ACCESS  	read-write
	STATUS 	current
	DESCRIPTION 
		"A user-defined description of the external sensor"
	::= { pduExternalSensorNamePlateEntry 3 }

pduExternalSensorNamePlateLocation  OBJECT-TYPE
	SYNTAX 	DisplayString
	MAX-ACCESS  	read-write
	STATUS 	current
	DESCRIPTION 
		"A user-defined string identifying the location of the PDU"
	::= { pduExternalSensorNamePlateEntry 4 }

pduExternalSensorNamePlateSerialNumber  OBJECT-TYPE
	SYNTAX 	DisplayString
	MAX-ACCESS  	read-only
	STATUS 	current
	DESCRIPTION 
		"The serial number of the external sensor being queried"
	::= { pduExternalSensorNamePlateEntry 5 }

pduExternalSensorNamePlateType  OBJECT-TYPE
	SYNTAX 	INTEGER {
		temperature (1),
		humidity (2),
		doorSwitch (3),
		dryContact (4),
		spotFluid (5),
		ropeFluid (6),
		smoke (7),
		beacon (8),
		airVelocity (9),
		modbusAdapter (17),
		hidAdapter (18),
		eHandleAdapter (19),
		assetmodule (25)
	}
	MAX-ACCESS  	read-only
	STATUS 	current
	DESCRIPTION 
		"The type of external sensor."
	::= { pduExternalSensorNamePlateEntry 6 }

pduExternalSensorNamePlateUnits  OBJECT-TYPE
	SYNTAX 	INTEGER {
		logic (0),
		degreeC (1),
		degreeF (2),
		percent (3),
		mps (4)
	}
	MAX-ACCESS  	read-only
	STATUS 	current
	DESCRIPTION 
		"The base units the external sensor is measured in. 
		This parameter does not apply to onOff, trip, vibration,
		 waterDetection, smokeDetection sensors. "
	::= { pduExternalSensorNamePlateEntry 7 }

pduExternalSensorNamePlateIdentifier  OBJECT-TYPE
	SYNTAX 	Integer32
	MAX-ACCESS  	read-only
	STATUS 	current
	DESCRIPTION 
		"Unique identifier of the external sensor."
	::= { pduExternalSensorNamePlateEntry 8 }

pduExternalSensorConfigTable  OBJECT-TYPE
	SYNTAX SEQUENCE OF PduExternalSensorConfigEntry
	MAX-ACCESS  	not-accessible
	STATUS 	current
	DESCRIPTION 
		"A table of PDU External Sensor configuration data"
	::= { pduExternalSensor 3 }

pduExternalSensorConfigEntry  OBJECT-TYPE
	SYNTAX 	PduExternalSensorConfigEntry
	MAX-ACCESS  	not-accessible
	STATUS 	current
	DESCRIPTION 
		"Configuration data from the PDU External 
		Sensor being queried"
	INDEX { pduUnitConfigIndex, pduExternalSensorConfigIndex }
	::= { pduExternalSensorConfigTable 1 }

PduExternalSensorConfigEntry ::= SEQUENCE {
	pduExternalSensorConfigIndex
		Integer32,
	pduExternalSensorConfigLowerCriticalThreshold
		Unsigned32,
	pduExternalSensorConfigLowerWarningThreshold
		Unsigned32,
	pduExternalSensorConfigUpperCriticalThreshold
		Unsigned32,
	pduExternalSensorConfigUpperWarningThreshold
		Unsigned32,
	pduExternalSensorConfigAlarmResetThreshold
		Unsigned32,
	pduExternalSensorConfigAlarmStateChangeDelay
		Unsigned32,
	pduExternalSensorConfigEnabledThresholds
		BITS,
	pduExternalSensorConfigAlarmState
		INTEGER
	}

pduExternalSensorConfigIndex  OBJECT-TYPE
	SYNTAX 	Integer32 (0..255)
	MAX-ACCESS  	not-accessible
	STATUS 	current
	DESCRIPTION 
		"The index of the PDU External Sensor 
		configuration table entry"
	::= { pduExternalSensorConfigEntry 1 }

pduExternalSensorConfigLowerCriticalThreshold  OBJECT-TYPE
	SYNTAX 	Unsigned32
	MAX-ACCESS  	read-write
	STATUS 	current
	DESCRIPTION 
		"User-defined lower critical alarm threshold in pduExternalSensorNamePlateUnits."
	::= { pduExternalSensorConfigEntry 2 }

pduExternalSensorConfigLowerWarningThreshold  OBJECT-TYPE
	SYNTAX 	Unsigned32
	MAX-ACCESS  	read-write
	STATUS 	current
	DESCRIPTION 
		"User-defined lower non-critical (warning) alarm threshold in pduExternalSensorNamePlateUnits."
	::= { pduExternalSensorConfigEntry 3 }

pduExternalSensorConfigUpperCriticalThreshold  OBJECT-TYPE
	SYNTAX 	Unsigned32
	MAX-ACCESS  	read-write
	STATUS 	current
	DESCRIPTION 
		"User-defined upper critical alarm threshold in pduExternalSensorNamePlateUnits."
	::= { pduExternalSensorConfigEntry 4 }

pduExternalSensorConfigUpperWarningThreshold  OBJECT-TYPE
	SYNTAX 	Unsigned32
	MAX-ACCESS  	read-write
	STATUS 	current
	DESCRIPTION 
		"User-defined upper non-critical (warning) alarm threshold in pduExternalSensorNamePlateUnits."
	::= { pduExternalSensorConfigEntry 5 }

pduExternalSensorConfigAlarmResetThreshold  OBJECT-TYPE
	SYNTAX 	Unsigned32
	MAX-ACCESS  	read-write
	STATUS 	current
	DESCRIPTION 
		"The hysteresis used for deassertions."
	::= { pduExternalSensorConfigEntry 6 }

pduExternalSensorConfigAlarmStateChangeDelay  OBJECT-TYPE
	SYNTAX 	Unsigned32
	MAX-ACCESS  	read-write
	STATUS 	current
	DESCRIPTION 
		"The delay measured in samples before a state is 
		asserted. If the value is zero, then the state is 
		asserted as soon as it is detected; if it is non-zero, 
		say n, then the assertion condition must exist for n+1 
		consecutive samples before the corresponding assertion 
		event is reported."
	::= { pduExternalSensorConfigEntry 7 }

pduExternalSensorConfigEnabledThresholds  OBJECT-TYPE
	SYNTAX 	BITS {
		lowerCritical (0),
		lowerWarning (1),
		upperWarning (2),
		upperCritical (3),
		binarySensorAlarm (4)
	}
	MAX-ACCESS  	read-write
	STATUS 	current
	DESCRIPTION 
		"A bit string indicating which alarm 
		thresholds are enabled.For binarySensorAlarm 0 to clear,for other
		4 to clear."
	::= { pduExternalSensorConfigEntry 8 }

pduExternalSensorConfigAlarmState OBJECT-TYPE
	SYNTAX 	INTEGER {
		on (1),
		off (0)
	}
	MAX-ACCESS  	read-write
	STATUS 	current
	DESCRIPTION 
		"User defined alarm state of external sensor"
	::= { pduExternalSensorConfigEntry 9 }
	
pduExternalSensorSTATUSTable  OBJECT-TYPE
	SYNTAX SEQUENCE OF PduExternalSensorSTATUSEntry
	MAX-ACCESS  	not-accessible
	STATUS 	current
	DESCRIPTION 
		"A table of PDU External Sensor STATUS data"
	::= { pduExternalSensor 4 }
	
pduExternalSensorSTATUSEntry  OBJECT-TYPE
	SYNTAX 	PduExternalSensorSTATUSEntry
	MAX-ACCESS  	not-accessible
	STATUS 	current
	DESCRIPTION 
		"STATUS data from the PDU External Sensor 
		being queried"
	INDEX { pduUnitSTATUSIndex, pduExternalSensorSTATUSIndex }
	::= { pduExternalSensorSTATUSTable 1 }

PduExternalSensorSTATUSEntry ::= SEQUENCE {
	pduExternalSensorSTATUSIndex
		Integer32,
	pduExternalSensorSTATUSName
		DisplayString,
	pduExternalSensorSTATUSAisle
		INTEGER,
	pduExternalSensorSTATUSCommSTATUS
		INTEGER,
	pduExternalSensorSTATUSState
		INTEGER,
	pduExternalSensorSTATUSValue
		Integer32,
	pduExternalSensorSTATUSTimeStamp
		DisplayString,
	pduExternalSensorSTATUSHighPrecisionValue
		Integer32
	}

pduExternalSensorSTATUSIndex  OBJECT-TYPE
	SYNTAX 	Integer32 (0..255)
	MAX-ACCESS  	not-accessible
	STATUS 	current
	DESCRIPTION 
		"The index of the PDU External Sensor STATUS table entry"
	::= { pduExternalSensorSTATUSEntry 1 }

pduExternalSensorSTATUSName  OBJECT-TYPE
	SYNTAX 	DisplayString
	MAX-ACCESS  	read-only
	STATUS 	current
	DESCRIPTION 
		"The user-defined name for the External Sensor"
	::= { pduExternalSensorSTATUSEntry 2 }

pduExternalSensorSTATUSAisle  OBJECT-TYPE
	SYNTAX 	INTEGER {
		hotAisle (1),
		coldAisle (2)
	}
	MAX-ACCESS  	read-only
	STATUS 	current
	DESCRIPTION 
		"Indicates whether the external sensor is 
		in a hot or cold aisle"
	::= { pduExternalSensorSTATUSEntry 3 }

pduExternalSensorSTATUSCommSTATUS  OBJECT-TYPE
	SYNTAX 	INTEGER {
		notInstalled (1),
		commsOk (2),
		commsLost (3)
	}
	MAX-ACCESS  	read-only
	STATUS 	current
	DESCRIPTION 
		"The communications STATUS of the sensor"
	::= { pduExternalSensorSTATUSEntry 4 }

pduExternalSensorSTATUSState  OBJECT-TYPE
	SYNTAX 	INTEGER {
		notPresent (0), alarmed (1), normal (2), belowLowerCritical (3), belowLowerWarning (4), aboveUpperWarning (5), aboveUpperCritical (6)
	}
	MAX-ACCESS  	read-only
	STATUS 	current
	DESCRIPTION 
		"This OID reports the current state of the sensor. 
			A notPresent (0) response indicates that no sensor is attached.
			An alarmed (1) response indicates that the sensor is present 
			and its measured reading indicates alarmed.
			A normal (2) response indicates that the sensor is present 
			and its measured reading lies within all thresholds.
			A belowLowerCritical (3) response indicates that the sensor 
			is present and its measured reading lies below the lower critical threshold.
			A belowLowerWarning (4) response indicates that the sensor 
			is present and its measured reading lies below the lower warning threshold.
			An aboveUpperWarning (5) response indicates that the sensor 
			is present and its measured reading lies above the upper warning threshold.
			An aboveUpperCritical (6) response indicates that the sensor 
			is present and its measured reading lies above the upper critical threshold."
	::= { pduExternalSensorSTATUSEntry 5 }

pduExternalSensorSTATUSValue  OBJECT-TYPE
	SYNTAX 	Integer32
	MAX-ACCESS  	read-only
	STATUS 	current
	DESCRIPTION 
		"Sensor reading in pduExternalSensorConfigUnits value."
	::= { pduExternalSensorSTATUSEntry 6 }

pduExternalSensorSTATUSTimeStamp  OBJECT-TYPE
	SYNTAX 	DisplayString
	MAX-ACCESS  	read-only
	STATUS 	current
	DESCRIPTION 
		"The sensor reading timestamp."
	::= { pduExternalSensorSTATUSEntry 7 }

pduExternalSensorSTATUSHighPrecisionValue  OBJECT-TYPE
	SYNTAX 	Integer32
	MAX-ACCESS  	read-only	
	STATUS 	current
	DESCRIPTION 
		"Temperature sensor reading in tenths of pduExternalSensorConfigUnits value.
		This OID is applied to temperature sensor only"
	::= { pduExternalSensorSTATUSEntry 8 }

-- Asset Manager

pduExternalAssetManagerTable  OBJECT-TYPE
	SYNTAX SEQUENCE OF PduExternalAssetManagerEntry
	MAX-ACCESS  	not-accessible
	STATUS 	current
	DESCRIPTION 
		"A table of PDU External Asset Manager data"
	::= { pduExternalSensor 5 }

pduExternalAssetManagerEntry  OBJECT-TYPE
	SYNTAX 	PduExternalAssetManagerEntry
	MAX-ACCESS  	not-accessible
	STATUS 	current
	DESCRIPTION 
		"Asset data from the PDU External 
		Sensor being queried"
	INDEX { pduUnitSTATUSIndex, pduExternalAssetManagerIndex }
	::= { pduExternalAssetManagerTable 1 }

PduExternalAssetManagerEntry ::= SEQUENCE {
	pduExternalAssetManagerIndex
		Integer32,
	pduExternalAssetULevel
		DisplayString,
	pduExternalAssetID
		DisplayString,
	pduExternalAssetBrand
		DisplayString,
	pduExternalAssetColorStandby
		Unsigned32,
    pduExternalAssetColorConnected
		Unsigned32,
	pduExternalMasterOrientation
		Unsigned32           
	}

pduExternalAssetManagerIndex  OBJECT-TYPE
	SYNTAX 	Integer32 (0..255)
	MAX-ACCESS  	not-accessible
	STATUS 	current
	DESCRIPTION 
		"The index of the PDU External Manager table entry"
	::= { pduExternalAssetManagerEntry 1 }


pduExternalAssetULevel  OBJECT-TYPE
	SYNTAX 	DisplayString
	MAX-ACCESS  	read-only
	STATUS 	current
	DESCRIPTION 
		"U-level position of Asset Module along with respective TagID"
	::= { pduExternalAssetManagerEntry 2 }

pduExternalAssetID  OBJECT-TYPE
	SYNTAX 	DisplayString
	MAX-ACCESS  	read-write
	STATUS 	current
	DESCRIPTION 
		"Asset ID (20 bytes alphanumeric ,No Special Char).Enter HEX and Read HEX values"
	::= { pduExternalAssetManagerEntry 3 }
pduExternalAssetBrand  OBJECT-TYPE
	SYNTAX 	DisplayString
	MAX-ACCESS  	read-write
	STATUS 	current
	DESCRIPTION 
		"Asset Brand(20 bytes alphanumeric ,No Special Char).Enter HEX and Read HEX values"
	::= { pduExternalAssetManagerEntry 4 }
pduExternalAssetColorStandby  OBJECT-TYPE
	SYNTAX 	Unsigned32
	MAX-ACCESS  	read-write
	STATUS 	current
	DESCRIPTION 
		"U-Level Light Color
		Not Bright 0, Red 1
		Purple 2, Yellow 3
		Green 4, Cyan 5
		Blue 6, White 7
		Red Flash 8, Purple Flash 9
		Yellow Flash 10, Green Flash 11
		Cyan Flash 12, Blue Flash 13
		White Flash 14	"
		
	::= { pduExternalAssetManagerEntry 5 }
pduExternalAssetColorConnected  OBJECT-TYPE
	SYNTAX 	Unsigned32
	MAX-ACCESS  	read-write
	STATUS 	current
	DESCRIPTION 
		"U-Level Light Color
		Not Bright 0, Red 1
		Purple 2, Yellow 3
		Green 4, Cyan 5
		Blue 6, White 7
		Red Flash 8, Purple Flash 9
		Yellow Flash 10, Green Flash 11
		Cyan Flash 12, Blue Flash 13
		White Flash 14	"
		
	::= { pduExternalAssetManagerEntry 6 }
pduExternalMasterOrientation  OBJECT-TYPE
	SYNTAX 	Unsigned32
	MAX-ACCESS  	read-write
	STATUS 	current
	DESCRIPTION 
		"Master Orientation ( 0 - bottom to top)(1- top to bottom) "
	::= { pduExternalAssetManagerEntry 7 }

--  Smart Cabinet

pduUnitSmartCabinetTableSize  OBJECT-TYPE
	SYNTAX 	Integer32 (0..255)
	MAX-ACCESS  	read-only
	STATUS 	current
	DESCRIPTION 
		"The total number of Smart Cabinet Configuration "
	::= { pduSmartCabinet 1 }

pduUnitSmartCabinetTable  OBJECT-TYPE
	SYNTAX SEQUENCE OF PduUnitSmartCabinetEntry
	MAX-ACCESS  	not-accessible
	STATUS 	current
	DESCRIPTION 
		"A table of Smart Cabinet information"
	::= { pduSmartCabinet 2 }


pduUnitSmartCabinetEntry  OBJECT-TYPE
	SYNTAX 	PduUnitSmartCabinetEntry
	MAX-ACCESS  	not-accessible
	STATUS 	current
	DESCRIPTION 
		"Information of Smart Cabinet"
	INDEX { pduUnitSmartCabinetIndex }
	::= { pduUnitSmartCabinetTable 1 }

PduUnitSmartCabinetEntry ::= SEQUENCE {
	pduUnitSmartCabinetIndex
		Integer32,
	pduUnitSmartCabinetCardUserName
		DisplayString,
	pduUnitSmartCabinetCardID
		Integer32,
	pduUnitSmartCabinetTimestamp
		DisplayString,
	pduUnitSmartCabinetDoor
		Integer32
	}

pduUnitSmartCabinetIndex   OBJECT-TYPE
	SYNTAX 	Integer32 (1..256)
	MAX-ACCESS  	not-accessible
	STATUS 	current
	DESCRIPTION 
		"The index of the PDU Smart Cabinet table entry"
	::= { pduUnitSmartCabinetEntry 1 }

pduUnitSmartCabinetCardUserName     OBJECT-TYPE
	SYNTAX 	DisplayString
	MAX-ACCESS  	read-write
	STATUS 	current
	DESCRIPTION 
		"User name of ID card"
	::= { pduUnitSmartCabinetEntry 2 }

pduUnitSmartCabinetCardID		OBJECT-TYPE
	SYNTAX 	Integer32
	MAX-ACCESS  	read-write
	STATUS 	current
	DESCRIPTION 
		"Card ID."
	::= { pduUnitSmartCabinetEntry 3 }

pduUnitSmartCabinetTimestamp	OBJECT-TYPE
	SYNTAX 	DisplayString
	MAX-ACCESS  	read-write
	STATUS 	current
	DESCRIPTION 
		"Indicates the date and time of information update"
	::= { pduUnitSmartCabinetEntry 4 }

pduUnitSmartCabinetDoor	OBJECT-TYPE
	SYNTAX 	INTEGER {
		hotAisle (1),
		coldAisle (2) }
	MAX-ACCESS  	read-write
	STATUS 	current
	DESCRIPTION 
		"Aisle of Smart Cabinet. "
	::= { pduUnitSmartCabinetEntry 5 }
		
pduUnitSmartCabinetControl  	OBJECT IDENTIFIER ::= { pduSmartCabinet 3 }

pduUnitSmartCabinetControlUserName  OBJECT-TYPE
	SYNTAX 	DisplayString
	MAX-ACCESS  	read-write
	STATUS 	current
	DESCRIPTION 
		"User name of ID card"
	::= { pduUnitSmartCabinetControl 1 }

pduUnitSmartCabinetControlCardID		OBJECT-TYPE
	SYNTAX 	Integer32
	MAX-ACCESS  	read-write
	STATUS 	current
	DESCRIPTION 
		"Card ID."
	::= { pduUnitSmartCabinetControl 2 }

pduUnitSmartCabinetControlTimestamp	OBJECT-TYPE
	SYNTAX 	DisplayString
	MAX-ACCESS  	read-write
	STATUS 	current
	DESCRIPTION 
		"Indicates the date and time of information update"
	::= { pduUnitSmartCabinetControl 3 }
	
pduUnitSmartCabinetControlDoor	OBJECT-TYPE
	SYNTAX 	INTEGER {
		hotAisle (1),
		coldAisle (2)
	}
	MAX-ACCESS  	read-write
	STATUS 	current
	DESCRIPTION 
		"Aisle of Smart Cabinet. "
	::= { pduUnitSmartCabinetControl 4 }
	
pduUnitSmartCabinetCardIDEdit	OBJECT-TYPE
	SYNTAX 	INTEGER {
		grant (0), remove (1)
	}
	MAX-ACCESS  	read-write
	STATUS 	current
	DESCRIPTION 
		"Smart Cabinet edit CardID "
	::= { pduUnitSmartCabinetControl 5 }
	
pduUnitSmartCabinetColdAisleLockSTATUS	OBJECT-TYPE
	SYNTAX 	INTEGER {
		unlock (0), lock (1), notPresent (2)
	}
	MAX-ACCESS  	read-write
	STATUS 	current
	DESCRIPTION 
		"Smart Cabinet ColdAisle lock state "
	::= { pduUnitSmartCabinetControl 6 }

pduUnitSmartCabinetHotAisleLockSTATUS	OBJECT-TYPE
	SYNTAX 	INTEGER {
		unlock (0), lock (1), notPresent (2)
	}
	MAX-ACCESS  	read-write
	STATUS 	current
	DESCRIPTION 
		"Smart Cabinet HotAisle lock state "
	::= { pduUnitSmartCabinetControl 7 }	

pduUnitSmartCabinetLockStateTable  OBJECT-TYPE
	SYNTAX SEQUENCE OF PduUnitSmartCabinetLockStateEntry
	MAX-ACCESS  	not-accessible
	STATUS 	current
	DESCRIPTION 
		"A table of Smart Cabinet aisle state control"
	::= { pduSmartCabinet 4 }

pduUnitSmartCabinetLockStateEntry  OBJECT-TYPE
	SYNTAX 	PduUnitSmartCabinetLockStateEntry
	MAX-ACCESS  	not-accessible
	STATUS 	current
	DESCRIPTION 
		"Information of Smart Cabinet Lock State"
	INDEX { pduUnitSmartCabinetLockStateIndex }
	::= { pduUnitSmartCabinetLockStateTable 1 }

PduUnitSmartCabinetLockStateEntry ::= SEQUENCE {
  pduUnitSmartCabinetLockStateIndex
  	Integer32,
	pduUnitSmartCabinetColdAisleLockState
		Integer32,
	pduUnitSmartCabinetHotAisleLockState
		Integer32,
	pduUnitSmartCabinetColdAisleLockLabel
		DisplayString,
	pduUnitSmartCabinetHotAisleLockLabel
		DisplayString
	}
	
pduUnitSmartCabinetLockStateIndex   OBJECT-TYPE
	SYNTAX 	Integer32 (1..256)
	MAX-ACCESS  	not-accessible
	STATUS 	current
	DESCRIPTION 
		"The index of the PDU Smart Cabinet table entry"
	::= { pduUnitSmartCabinetLockStateEntry 1 }	

pduUnitSmartCabinetColdAisleLockState	OBJECT-TYPE
	SYNTAX 	INTEGER {
		unlock (0), lock (1), notPresent (2)
	}
	MAX-ACCESS  	read-write
	STATUS 	current
	DESCRIPTION 
		"Smart Cabinet ColdAisle lock state "
	::= { pduUnitSmartCabinetLockStateEntry 2 }

pduUnitSmartCabinetHotAisleLockState	OBJECT-TYPE
	SYNTAX 	INTEGER {
		unlock (0), lock (1), notPresent (2)
	}
	MAX-ACCESS  	read-write
	STATUS 	current
	DESCRIPTION 
		"Smart Cabinet HotAisle lock state "
	::= { pduUnitSmartCabinetLockStateEntry 3 }		

pduUnitSmartCabinetColdAisleLockLabel  OBJECT-TYPE
	SYNTAX 	DisplayString
	MAX-ACCESS  	read-only
	STATUS 	current
	DESCRIPTION 
		"Label of cold aisle smartcabinet"
	::= { pduUnitSmartCabinetLockStateEntry 4 }
				
pduUnitSmartCabinetHotAisleLockLabel  OBJECT-TYPE
	SYNTAX 	DisplayString
	MAX-ACCESS  	read-only
	STATUS 	current
	DESCRIPTION 
		"Label of hot aisle smartcabinet"
	::= { pduUnitSmartCabinetLockStateEntry 5 }					
				
-- Traps Information
trapsInfo  OBJECT IDENTIFIER ::= { pduTraps 1 }

trapsInfoTable  OBJECT-TYPE
	SYNTAX SEQUENCE OF TrapsInfoEntry
	MAX-ACCESS  	not-accessible
	STATUS 	current
	DESCRIPTION 
       "A list of Trap Information entries. The number of
            entries are given by the value of pduUnitTableSize."	
	::= { trapsInfo 1 }
	
trapsInfoEntry  OBJECT-TYPE
	SYNTAX 	TrapsInfoEntry
	MAX-ACCESS  	not-accessible
	STATUS 	current
	DESCRIPTION 
		"An entry containing objects used in traps"
	INDEX { trapsInfoIndex }
	::= { trapsInfoTable 1 }

TrapsInfoEntry ::= SEQUENCE {
	trapsInfoIndex
		Integer32,
	userName
		DisplayString,
	userUpdated
		DisplayString,
	firmwareVersion
		DisplayString,
	roleUpdated
		DisplayString,
	smtpRecipients
		DisplayString,
	smtpServer
		DisplayString
	}

trapsInfoIndex  OBJECT-TYPE
	SYNTAX 	Integer32 (1..256)
	MAX-ACCESS  	not-accessible
	STATUS 	current
	DESCRIPTION 
		"The index of the traps table entry"
	::= { trapsInfoEntry 1 }


userName  OBJECT-TYPE
	SYNTAX 	DisplayString
	MAX-ACCESS  	read-only
	STATUS 	current
	DESCRIPTION 
		"The user currently logged in."
	::= { trapsInfoEntry 2 }
	
userUpdated  OBJECT-TYPE
	SYNTAX 	DisplayString
	MAX-ACCESS  	read-only
	STATUS 	current
	DESCRIPTION 
		"The user added, deleted, or modified."
	::= { trapsInfoEntry 3 }

firmwareVersion  OBJECT-TYPE
	SYNTAX 	DisplayString
	MAX-ACCESS  	read-only
	STATUS 	current
	DESCRIPTION 
		"The version of Firmware."
	::= { trapsInfoEntry 4 }

roleUpdated  OBJECT-TYPE
	SYNTAX 	DisplayString
	MAX-ACCESS  	read-only
	STATUS 	current
	DESCRIPTION 
		"The role added, deleted, or modified."
	::= { trapsInfoEntry 5 }

smtpRecipients  OBJECT-TYPE
	SYNTAX 	DisplayString
	MAX-ACCESS  	read-only
	STATUS 	current
	DESCRIPTION 
		"Comma separated list of SMTP  recipients"
	::= { trapsInfoEntry 6 }

smtpServer  OBJECT-TYPE
	SYNTAX 	DisplayString
	MAX-ACCESS  	read-only
	STATUS 	current
	DESCRIPTION 
		"The IP address/host name of the SMTP server"
	::= { trapsInfoEntry 7 }

pduIndex  OBJECT-TYPE
	SYNTAX 	Integer32
	MAX-ACCESS  	accessible-for-notify
	STATUS 	current
	DESCRIPTION 
		"A unique value for PDU. Its value ranges between 1 
		and the value of PDU count"
	::= { trapsInfo 2 }

externalSensorIndex  OBJECT-TYPE
	SYNTAX 	Integer32
	MAX-ACCESS  	accessible-for-notify
	STATUS 	current
	DESCRIPTION 
		"A unique value for each sensor. Its value ranges between 1 
		and the value of external sensor count."
	::= { trapsInfo 3 }

serverPing  OBJECT-TYPE
	SYNTAX 	INTEGER {
		pingEnable (1),
		pingDisable (2),
		serverReachable (3),
		serverNotReachable (4)
	}
	MAX-ACCESS  	accessible-for-notify
	STATUS 	current
	DESCRIPTION 
		"Whether server ping has been enabled or disabled and 
		whether the server is reachable or not reachable"
	::= { trapsInfo 4 }

usbDevice  OBJECT-TYPE
	SYNTAX 	INTEGER {
		connected (1),
		disconnected (2)
	}
	MAX-ACCESS  	accessible-for-notify
	STATUS 	current
	DESCRIPTION 
		"Whether a USB device has been connected or disconnected"
	::= { trapsInfo 5 }

errorDescription  OBJECT-TYPE
	SYNTAX 	DisplayString
	MAX-ACCESS  	accessible-for-notify
	STATUS 	current
	DESCRIPTION 
		"Description of the Error"
	::= { trapsInfo 6 }

daisyChain  OBJECT-TYPE
	SYNTAX 	INTEGER {
		connected (1),
		disconnected (2)
	}
	MAX-ACCESS  	accessible-for-notify
	STATUS 	current
	DESCRIPTION 
		"Whether a daisy chain member has been connected or disconnected"
	::= { trapsInfo 7 }

systemCommunication  OBJECT-TYPE
	SYNTAX 	INTEGER {
		ok (1),
		lost (2)
	}
	MAX-ACCESS  	accessible-for-notify
	STATUS 	current
	DESCRIPTION 
		"Whether the Network management card has lost contact with daisy a chain member."
	::= { trapsInfo 8 }

trapCode OBJECT-TYPE
	SYNTAX INTEGER
	MAX-ACCESS read-only
	STATUS current
	DESCRIPTION
		"A number identifying the event for the trap that was sent.
		 Mapped unique trap code per unique event to be used by ISEE's
		 decoder ring."
	::= { trapsInfo 9 }

trapDescription OBJECT-TYPE
	SYNTAX DisplayString (SIZE (0..255))
	MAX-ACCESS read-only
	STATUS current
	DESCRIPTION
		"A string identifying the event for that last trap that was sent."
	::= { trapsInfo 10 }

networkCardStart  		NOTIFICATION-TYPE
				OBJECTS {   pduIndex,
						pduNamePlateName,
			 		    pduNamePlateInetAddressType,
					    pduNamePlateIPAddress,
					    sysContact,
					    sysName,
					    sysLocation  }
				STATUS 	current
				DESCRIPTION 
					"The network card has started"
				::= { pduTraps 2 }
	
networkCardReset  		NOTIFICATION-TYPE
				OBJECTS {   pduIndex,
						pduNamePlateName,
			 		    userName,
					    pduNamePlateInetAddressType,
					    pduNamePlateIPAddress,
					    sysContact,
					    sysName,
					    sysLocation }
				STATUS 	current
				DESCRIPTION 
					"The network card was reset via the web or command line interface."
				::= { pduTraps 3 }
	
userLogin  			NOTIFICATION-TYPE
				OBJECTS {   pduIndex,
						pduNamePlateName, 
    					userName, 
					    pduNamePlateInetAddressType,
					    pduNamePlateIPAddress,
					    sysContact,
					    sysName,
					    sysLocation }
				STATUS 	current
				DESCRIPTION 
					"A user logged in"
				::= { pduTraps 4 }

userLogoff  			NOTIFICATION-TYPE
				OBJECTS {   pduIndex,
							pduNamePlateName, 
    					    userName, 
					    pduNamePlateInetAddressType,
					    pduNamePlateIPAddress,
					    sysContact,
					    sysName,
					    sysLocation }
				STATUS 	current
				DESCRIPTION 
					" A user logged off"
				::= { pduTraps 5 }

userAuthenticationFailed  	NOTIFICATION-TYPE
				OBJECTS {   pduIndex,
							pduNamePlateName, 
    					    userName, 
					    pduNamePlateInetAddressType,
					    pduNamePlateIPAddress,
					    sysContact,
					    sysName,
					    sysLocation }
				STATUS 	current
				DESCRIPTION 
					"A user authentication attempt failed."
				::= { pduTraps 6 }
	
userSessionTimeout  		NOTIFICATION-TYPE
				OBJECTS {   pduIndex,
							pduNamePlateName, 
    					    userName, 
					    pduNamePlateInetAddressType,
					    pduNamePlateIPAddress,
					    sysContact,
					    sysName,
					    sysLocation }
				STATUS 	current
				DESCRIPTION 
					"A user session timed out"
				::= { pduTraps 7 }

userAdded  			NOTIFICATION-TYPE
				OBJECTS {   pduIndex,
							pduNamePlateName, 
    					    userName, 
    					    pduNamePlateInetAddressType,
					    pduNamePlateIPAddress,
    					    userUpdated,
    					    sysContact,
					    sysName,
					    sysLocation }
				STATUS 	current
				DESCRIPTION 
					"A user account was added to system."
				::= { pduTraps 8 }
	
userModified  			NOTIFICATION-TYPE
				OBJECTS {   pduIndex,
							pduNamePlateName, 
    					    userName, 
    					    pduNamePlateInetAddressType,
					    pduNamePlateIPAddress,
    					    userUpdated,
    					    sysContact,
					    sysName,
					    sysLocation }
				STATUS 	current
				DESCRIPTION 
					"A user account was modified."
				::= { pduTraps 9 }
	
userDeleted  			NOTIFICATION-TYPE
				OBJECTS {   pduIndex,
							pduNamePlateName, 
    					    userName, 
    					    pduNamePlateInetAddressType,
					    pduNamePlateIPAddress,
    					    userUpdated,
    					    sysContact,
					    sysName,
					    sysLocation }
				STATUS 	current
				DESCRIPTION 
					"A user account was deleted."
				::= { pduTraps 10 }

roleAdded  			NOTIFICATION-TYPE
				OBJECTS {   pduIndex,
							pduNamePlateName, 
    					    userName, 
					    pduNamePlateInetAddressType,
					    pduNamePlateIPAddress,
					    roleUpdated,
    					    sysContact,
					    sysName,
					    sysLocation }
				STATUS 	current
				DESCRIPTION 
					"A user role was added."
				::= { pduTraps 11 }
	
roleModified  			NOTIFICATION-TYPE
				OBJECTS {   pduIndex,
							pduNamePlateName, 
    					    userName, 
					    pduNamePlateInetAddressType,
					    pduNamePlateIPAddress,
					    roleUpdated,
    					    sysContact,
					    sysName,
					    sysLocation }
				STATUS 	current
				DESCRIPTION 
					"A user role was modified."
				::= { pduTraps 12 }

roleDeleted  			NOTIFICATION-TYPE
				OBJECTS {   pduIndex,
							pduNamePlateName, 
    					    userName, 
					    pduNamePlateInetAddressType,
					    pduNamePlateIPAddress,
					    roleUpdated,
    					    sysContact,
					    sysName,
					    sysLocation }
				STATUS 	current
				DESCRIPTION 
					"A user role was deleted."
				::= { pduTraps 13 }

firmwareUpdateStarted  	NOTIFICATION-TYPE
				OBJECTS {   pduIndex,
							pduNamePlateName, 
    					    userName, 
					    pduNamePlateInetAddressType,
					    pduNamePlateIPAddress,
					    firmwareVersion,
    					    sysContact,
					    sysName,
					    sysLocation }
				STATUS 	current
				DESCRIPTION 
					"A firmware update has started."
				::= { pduTraps 14 }

firmwareUpdateCompleted  	NOTIFICATION-TYPE
				OBJECTS {   pduIndex,
							pduNamePlateName, 
    					    userName, 
					    pduNamePlateInetAddressType,
					    pduNamePlateIPAddress,
					    firmwareVersion,
    					    sysContact,
					    sysName,
					    sysLocation }
				STATUS 	current
				DESCRIPTION 
					"The firmware update has completed."
				::= { pduTraps 15 }
	
userBlocked  			NOTIFICATION-TYPE
				OBJECTS {   pduIndex,
							pduNamePlateName, 
    					    userName, 
					    pduNamePlateInetAddressType,
					    pduNamePlateIPAddress,
					    sysContact,
					    sysName,
					    sysLocation }
				STATUS 	current
				DESCRIPTION 
					"A user is blocked."
				::= { pduTraps 16 }
	
outletControl  			NOTIFICATION-TYPE
				OBJECTS {   pduIndex,
							pduNamePlateName, 
    	 				    userName, 
	  				    pduNamePlateInetAddressType,
	  				    pduNamePlateIPAddress,
	  				    pduOutletSwitchedControlNumber,
	  				    pduOutletSwitchedSTATUSState, 
	  				    pduOutletSwitchedControlCommand,
	  				    sysContact,
	  				    sysName,
	  				    sysLocation }
				STATUS 	current
				DESCRIPTION 
					"Outlet control operation applied."
				::= { pduTraps 17 }

userPasswordChange  		NOTIFICATION-TYPE
				OBJECTS {   pduIndex,
							pduNamePlateName, 
    					    userName, 
    				    	    pduNamePlateInetAddressType,
					    pduNamePlateIPAddress,
    					    userUpdated,
    					    sysContact,
					    sysName,
					    sysLocation }
				STATUS 	current
				DESCRIPTION 
					"A user password was changed. "
				::= { pduTraps 18 }
	
passwordSettingsChange  	NOTIFICATION-TYPE
				OBJECTS {   pduIndex,
							pduNamePlateName, 
    					    userName, 
					    pduNamePlateInetAddressType,
					    pduNamePlateIPAddress,
					    sysContact,
					    sysName,
					    sysLocation }
				STATUS 	current
				DESCRIPTION 
					"One or more password policy settings were changed."
				::= { pduTraps 19 }

logFileCleared  			NOTIFICATION-TYPE
				OBJECTS {   pduIndex,
							pduNamePlateName, 
    					    userName, 
					    pduNamePlateInetAddressType,
					    pduNamePlateIPAddress,
					    sysContact,
					    sysName,
					    sysLocation }
				STATUS 	current
				DESCRIPTION 
					"The log file has been cleared."
				::= { pduTraps 21 }
	
pduConfigurationFileImported  	NOTIFICATION-TYPE
				OBJECTS {   pduIndex,
							pduNamePlateName, 
    					    userName, 
					    pduNamePlateInetAddressType,
					    pduNamePlateIPAddress,
					    sysContact,
					    sysName,
					    sysLocation }
				STATUS 	current
				DESCRIPTION 
					"PDU configuration file was imported."
				::= { pduTraps 22 }

pduConfigurationFileExported  	NOTIFICATION-TYPE
				OBJECTS {   pduIndex,
							pduNamePlateName, 
    					    userName, 
					    pduNamePlateInetAddressType,
					    pduNamePlateIPAddress,
					    sysContact,
					    sysName,
					    sysLocation }
				STATUS 	current
				DESCRIPTION 
					"PDU configuration file was exported"
				::= { pduTraps 23 }

pduUnitActivePowerStateChange  NOTIFICATION-TYPE
				OBJECTS {   pduIndex,
							pduNamePlateName, 
    	  				    pduNamePlateInetAddressType,
	  				    pduNamePlateIPAddress,
	  				    pduUnitSTATUSLoadState,
	  				    pduUnitSTATUSActivePower,
	  				    sysContact,
	  				    sysName,
	  				    sysLocation }
				STATUS 	current
				DESCRIPTION 
					"PDU unit active power state changes."
				::= { pduTraps 24 }
	
pduInputphaseVoltageStateChange  	NOTIFICATION-TYPE
					OBJECTS {   pduIndex,
								pduNamePlateName, 
    	  					    pduNamePlateInetAddressType,
	  					    pduNamePlateIPAddress,
	  					    pduInputPhaseSTATUSCount, 
	  					    pduInputPhaseSTATUSVoltageState, 
	  					    pduInputPhaseSTATUSVoltage,
	  					    sysContact,
	  					    sysName,
	  					    sysLocation }
					STATUS 	current
					DESCRIPTION 
						"PDU input phase voltage state changes."
				::= { pduTraps 25 }
	
pduInputphaseCurrentStateChange  	NOTIFICATION-TYPE
					OBJECTS {   pduIndex,
								pduNamePlateName, 
    	  					    pduNamePlateInetAddressType,
	  					    pduNamePlateIPAddress,
	  					    pduInputPhaseSTATUSCount, 
	  					    pduInputPhaseSTATUSCurrentState, 
	  					    pduInputPhaseSTATUSCurrent,
	  					    sysContact,
	  					    sysName,
	  					    sysLocation }
					STATUS 	current
					DESCRIPTION 
						"PDU input phase Current state changes."
				::= { pduTraps 26 }
	
pduCircuitBreakerCurrentStateChange  NOTIFICATION-TYPE
					OBJECTS {   pduIndex,
								pduNamePlateName, 
    	  					    pduNamePlateInetAddressType,
	  					    pduNamePlateIPAddress,
	  					    pduCircuitBreakerSTATUSIndex, 
	  					    pduCircuitBreakerSTATUSLoadState, 
	  					    pduCircuitBreakerSTATUSCurrent,
						    pduCircuitBreakerSTATUSPowerFactor,
	  					    sysContact,
	  					    sysName,
	  					    sysLocation }
					STATUS 	current
					DESCRIPTION 
						"PDU Circuit Breaker Current state changes."
				::= { pduTraps 27 }

pduOutletActivePowerStateChange  	NOTIFICATION-TYPE
					OBJECTS {   pduIndex,
								pduNamePlateName, 
    	  					    pduNamePlateInetAddressType,
	  					    pduNamePlateIPAddress,
	  					    pduOutletMeteredSTATUSIndex, 
	  					    pduOutletMeteredSTATUSLoadState, 
	  					    pduOutletMeteredSTATUSActivePower,
	  					    sysContact,
	  					    sysName,
	  					    sysLocation }
					STATUS 	current
					DESCRIPTION 
						"PDU Metered Outlet Active Power state changes."
				::= { pduTraps 28 }

pduExternalSensorStateChange  NOTIFICATION-TYPE
				OBJECTS {   pduIndex,
							pduNamePlateName, 
    	  				    pduNamePlateInetAddressType,
	  				    pduNamePlateIPAddress,
	  				    pduExternalSensorSTATUSIndex, 
	  				    pduExternalSensorSTATUSName, 
	  				    pduExternalSensorNamePlateType, 
					    pduExternalSensorSTATUSAisle, 
					    pduExternalSensorNamePlateUnits, 
					    pduExternalSensorSTATUSState, 
					    pduExternalSensorSTATUSValue,
	  				    sysContact,
	  				    sysName,
	  				    sysLocation }
				STATUS 	current
				DESCRIPTION 
					"PDU External Sensor state changes."
				::= { pduTraps 29 }

smtpTransmissionFailure  	NOTIFICATION-TYPE
				OBJECTS {   pduIndex,
							pduNamePlateName, 
    	  				    pduNamePlateInetAddressType,
	  				    pduNamePlateIPAddress,
	  				    smtpRecipients,
	  				    smtpServer,
	  				    sysContact,
	  				    sysName,
    					    sysLocation }
				STATUS 	current
				DESCRIPTION 
					"SMTP message transmission failed."
				::= { pduTraps 30 }
	
ldapError  			NOTIFICATION-TYPE
				OBJECTS {   pduIndex,
							pduNamePlateName, 
    	  				    pduNamePlateInetAddressType,
	  				    pduNamePlateIPAddress,
	  				    errorDescription,
	  				    sysContact,
	  				    sysName,
	  				    sysLocation }
				STATUS 	current
				DESCRIPTION 
					"A LDAP error occurred"
				::= { pduTraps 31 }
				
firmwareUpdateFailed  		NOTIFICATION-TYPE
				OBJECTS {   pduIndex,
							pduNamePlateName, 
    					    userName, 
					    pduNamePlateInetAddressType,
					    pduNamePlateIPAddress,
					    firmwareVersion,
    					    sysContact,
					    sysName,
					    sysLocation }
				STATUS 	current
				DESCRIPTION 
					"A firmware update has failed."
				::= { pduTraps 32 }
	
serverPingState 		NOTIFICATION-TYPE
				OBJECTS {   
						pduIndex,
						pduNamePlateName, 
    	  				userName,
	  				    pduNamePlateInetAddressType,
	  				    pduNamePlateIPAddress,
	  				    serverPing,
    					sysContact,
	  				    sysName,
	  				    sysLocation }
				STATUS 	current
				DESCRIPTION 
					"The Ping feature has been enabled."
				::= { pduTraps 33 }
	
bootloaderState 		NOTIFICATION-TYPE
				OBJECTS {   pduIndex,
							pduNamePlateName, 
    	  				    pduNamePlateInetAddressType,
	  				    pduNamePlateIPAddress,
    					sysContact,
	  				    sysName,
	  				    sysLocation }
				STATUS 	current
				DESCRIPTION 
					"Enter into Bootloader mode"
				::= { pduTraps 34 }

daisyChainState 		NOTIFICATION-TYPE
				OBJECTS {   pduIndex,
							pduNamePlateName, 
    	  				    pduNamePlateInetAddressType,
	  				    pduNamePlateIPAddress,
	  				    daisyChain,
    					sysContact,
	  				    sysName,
	  				    sysLocation }
				STATUS 	current
				DESCRIPTION 
					"A daisy chain member has been connected or disconnected."
				::= { pduTraps 35 }
	
systemInternalCommunicationLost  	NOTIFICATION-TYPE
					OBJECTS {   pduIndex,
								pduNamePlateName, 
    	  				    	pduNamePlateInetAddressType,
	  				    	    pduNamePlateIPAddress,
	  				    	    systemCommunication,
    	    					    sysContact,
	  				    	    sysName,
	  				   	    sysLocation }
					STATUS 	current
					DESCRIPTION 
						"Network management card has lost contaction with internal boards."
				::= { pduTraps 36 }


smartCabinetLockUnlocked			NOTIFICATION-TYPE
					OBJECTS {   pduIndex,
							pduNamePlateName, 
    	  				    	pduNamePlateInetAddressType,
	  				    	    pduNamePlateIPAddress,
						    pduUnitSmartCabinetDoor,
						    pduExternalSensorSTATUSValue,
    	    					    sysContact,
	  				    	    sysName,
	  				   	    sysLocation }
					STATUS 	current
					DESCRIPTION 
						"The Cabinet lock is unlocked."
				::= { pduTraps 37 }

smartCabinetLockLocked			NOTIFICATION-TYPE
					OBJECTS {   pduIndex,
							pduNamePlateName, 
    	  				    	pduNamePlateInetAddressType,
	  				    	    pduNamePlateIPAddress,
						    pduUnitSmartCabinetDoor,
						    pduExternalSensorSTATUSValue,
    	    					    sysContact,
	  				    	    sysName,
	  				   	    sysLocation }
					STATUS 	current
					DESCRIPTION 
						"The Cabinet lock is locked"
				::= { pduTraps 38 }

smartCabinetSwapCard		NOTIFICATION-TYPE
					OBJECTS {   pduIndex,
							pduNamePlateName, 
    	  				    	pduNamePlateInetAddressType,
	  				    	    pduNamePlateIPAddress,
						    pduUnitSmartCabinetDoor,
						    pduUnitSmartCabinetCardID,
						    pduExternalSensorSTATUSValue,
    	    					    sysContact,
	  				    	    sysName,
	  				   	    sysLocation }
					STATUS 	current
					DESCRIPTION 
						"Card is swapped"
				::= { pduTraps 39 }

smartCabinetLockerLockDoorOpen		NOTIFICATION-TYPE
					OBJECTS {   pduIndex,
							pduNamePlateName, 
    	  				    	pduNamePlateInetAddressType,
	  				    	    pduNamePlateIPAddress,
						    pduUnitSmartCabinetDoor,
						    pduExternalSensorSTATUSValue,
    	    					    sysContact,
	  				    	    sysName,
	  				   	    sysLocation }
					STATUS 	current
					DESCRIPTION 
						"Locker locked but door open"
				::= { pduTraps 40 }
				
smartCabinetLockerUnlockDoorClose		NOTIFICATION-TYPE
					OBJECTS {   pduIndex,
							pduNamePlateName, 
    	  				    	pduNamePlateInetAddressType,
	  				    	    pduNamePlateIPAddress,
						    pduUnitSmartCabinetDoor,
						    pduExternalSensorSTATUSValue,
    	    					    sysContact,
	  				    	    sysName,
	  				   	    sysLocation }
					STATUS 	current
					DESCRIPTION 
						"Locker unlocked but door close"
				::= { pduTraps 41 }				
pdusmartCabinetLockerAutolock		NOTIFICATION-TYPE
					OBJECTS {   pduIndex,
							pduNamePlateName, 
    	  				    	pduNamePlateInetAddressType,
	  				    	    pduNamePlateIPAddress,
						    pduExternalSensorSTATUSValue,
    	    					    sysContact,
	  				    	    sysName,
	  				   	    sysLocation }
					STATUS 	current
					DESCRIPTION 
						"The cabinet locker is locked automatically"
				::= { pduTraps 42 }		
				
pdusmartCabinetDoorOpen		NOTIFICATION-TYPE
					OBJECTS {   pduIndex,
							pduNamePlateName, 
    	  				    	pduNamePlateInetAddressType,
	  				    	    pduNamePlateIPAddress,
						    pduExternalSensorSTATUSValue,
    	    					    sysContact,
	  				    	    sysName,
	  				   	    sysLocation }
					STATUS 	current
					DESCRIPTION 
						"The cabinet door is  open"
				::= { pduTraps 43 }	
				
pdusmartCabinetDoorLock		NOTIFICATION-TYPE
					OBJECTS {   pduIndex,
							pduNamePlateName, 
    	  				    	pduNamePlateInetAddressType,
	  				    	    pduNamePlateIPAddress,
						    pduExternalSensorSTATUSValue,
    	    					    sysContact,
	  				    	    sysName,
	  				   	    sysLocation }
					STATUS 	current
					DESCRIPTION 
						"The cabinet  door is locked"
				::= { pduTraps 44 }										

pdusmartCabinetDoorUnlock		NOTIFICATION-TYPE
					OBJECTS {   pduIndex,
							pduNamePlateName, 
    	  				    	pduNamePlateInetAddressType,
	  				    	    pduNamePlateIPAddress,
						    pduExternalSensorSTATUSValue,
    	    					    sysContact,
	  				    	    sysName,
	  				   	    sysLocation }
					STATUS 	current
					DESCRIPTION 
						"The cabinet door is unlocked"
				::= { pduTraps 45 }			

pdusmartCabinetAllDoorLock		NOTIFICATION-TYPE
					OBJECTS {   pduIndex,
							pduNamePlateName, 
    	  				    	pduNamePlateInetAddressType,
	  				    	    pduNamePlateIPAddress,
						    pduExternalSensorSTATUSValue,
    	    					    sysContact,
	  				    	    sysName,
	  				   	    sysLocation }
					STATUS 	current
					DESCRIPTION 
						"All cabinet door is locked"
				::= { pduTraps 46 }		
				
systemReboot	  		NOTIFICATION-TYPE
				OBJECTS {   pduIndex,
						pduNamePlateName,
			 		    pduNamePlateInetAddressType,
					    pduNamePlateIPAddress,
					    sysContact,
					    sysName,
					    sysLocation  }
				STATUS 	current
				DESCRIPTION 
					"System has rebooted"
				::= { pduTraps 50 }


trapCritical 			NOTIFICATION-TYPE
				OBJECTS  {
	             				trapCode, 
	             				trapDescription, 
	             				sysDescr, 
	             				pduNamePlateIPAddress}
        			STATUS      current
				DESCRIPTION
        				"A critical alarm has occurred."
        			::= {pduTraps  51}

trapWarning 			NOTIFICATION-TYPE
				OBJECTS  { 
					     trapCode, 
					     trapDescription, 
					     sysDescr, 
					     pduNamePlateIPAddress}
				STATUS      current
				DESCRIPTION
				"A warning alarm has occurred."
				::= {pduTraps  52}

trapInformation 		NOTIFICATION-TYPE
				OBJECTS  {
					     trapCode, 
					     trapDescription, 
					     sysDescr, 
					     pduNamePlateIPAddress }
				STATUS      current
				DESCRIPTION
				"An informational alarm has occurred."
				::= {pduTraps  53}

trapCleared 			NOTIFICATION-TYPE
				OBJECTS  {
					     trapCode, 
					     trapDescription, 
					     sysDescr, 
					     pduNamePlateIPAddress}
				STATUS      current
				DESCRIPTION
				"An alarm has cleared."
				::= {pduTraps  54}

trapTest 			NOTIFICATION-TYPE
				OBJECTS  {
					     trapCode,
						     trapDescription,
					     sysDescr, 
					     pduNamePlateIPAddress} 
				STATUS      current
				DESCRIPTION
				"Test trap sent to a trap receiver to check proper reception of traps" 
				::= {pduTraps  55}

--     ======Hid Table  ==========
--     ======Hid Sensor STATUS==========
pduEhandleTable OBJECT-TYPE
    SYNTAX SEQUENCE OF PduEhandleEntry
    MAX-ACCESS not-accessible
    STATUS current
    DESCRIPTION
        "A list of contact sensors.  The number of entries are
         given by number of pdu and pduEhandleCount."
    ::= { pduEhandle 1 }

pduEhandleEntry OBJECT-TYPE
    SYNTAX PduEhandleEntry
    MAX-ACCESS not-accessible
    STATUS current
    DESCRIPTION
        "An entry for a contact sensor"
    INDEX { pduEhandleIndex }
    ::= { pduEhandleTable 1 }

PduEhandleEntry ::= SEQUENCE
    {
        pduEhandleIndex              INTEGER,
        pduEhandleAisle              INTEGER,
        pduEhandleHandleOperation    INTEGER,
        pduEhandleFwVer                  DisplayString,
        pduEhandleMechanicalLock        INTEGER,
        pduEhandleSerial               DisplayString,
        pduEhandleHwVer                DisplayString,
        pduEhandleAutoLockTime       INTEGER,
        pduEhandleDoorOpenTime       INTEGER,
        pduEhandleMaxDoorOpenTime    INTEGER,
        pduEhandleUserPinLength      INTEGER,
        pduEhandleUserPinMode        INTEGER,
        pduEhandleAisleControl       INTEGER
     }

pduEhandleIndex OBJECT-TYPE
    SYNTAX INTEGER (1..2)
    MAX-ACCESS read-only
    STATUS current
    DESCRIPTION
        "The index of the PDU HID table entry"
    ::= { pduEhandleEntry 1 }

pduEhandleAisle OBJECT-TYPE
    SYNTAX INTEGER
        {
            hot(1),
            cold(2)
        }
    MAX-ACCESS read-only
    STATUS current
    DESCRIPTION
        "Aisle of HID handle. "
    ::= { pduEhandleEntry 2 }

pduEhandleHandleOperation OBJECT-TYPE
    SYNTAX INTEGER
        {
            unlock(1),
            lock(2)
        }
    MAX-ACCESS read-write
    STATUS current
    DESCRIPTION
        "HID handle control opterations "
    ::= { pduEhandleEntry 3 }

pduEhandleFwVer OBJECT-TYPE
    SYNTAX DisplayString
    MAX-ACCESS read-only
    STATUS current
    DESCRIPTION
        "The firmware revision level of the HID"
    ::= { pduEhandleEntry 4 }

pduEhandleMechanicalLock OBJECT-TYPE
    SYNTAX INTEGER
        {
            unlock(1),
            lock(2)
        }
    MAX-ACCESS read-only
    STATUS current
    DESCRIPTION
        "HID Mechanical opterations "
    ::= { pduEhandleEntry 5 }

pduEhandleSerial OBJECT-TYPE
    SYNTAX DisplayString
    MAX-ACCESS read-only
    STATUS current
    DESCRIPTION
        "The Serial Number of the HID"
    ::= { pduEhandleEntry 6 }

pduEhandleHwVer OBJECT-TYPE
    SYNTAX DisplayString
    MAX-ACCESS read-only
    STATUS current
    DESCRIPTION
        "The hardware revision level of the HID"
    ::= { pduEhandleEntry 7 }

pduEhandleAutoLockTime OBJECT-TYPE
SYNTAX INTEGER
    MAX-ACCESS read-write
    STATUS current
    DESCRIPTION
        "HID Electronic Latch Autolock Time in seconds, Value ranges (0-999) "
::= { pduEhandleEntry 8 }

pduEhandleDoorOpenTime OBJECT-TYPE
    SYNTAX INTEGER
    MAX-ACCESS read-write
    STATUS current
    DESCRIPTION
        "HID Door Open Time in seconds, Value ranges (0-999)"
        ::= { pduEhandleEntry 9 }

pduEhandleMaxDoorOpenTime OBJECT-TYPE
    SYNTAX INTEGER
    MAX-ACCESS read-write
    STATUS current
    DESCRIPTION
        "HID Max Door Open Time in seconds, Value ranges (0-32400),
         critical alarm will be raised if door is left open past this time"
    ::= { pduEhandleEntry 10 }

pduEhandleUserPinLength OBJECT-TYPE
    SYNTAX INTEGER
    MAX-ACCESS read-write
    STATUS current
    DESCRIPTION
        "Rack MAX-ACCESS User minimum PIN Length, value ranges(1-15)"
    ::= { pduEhandleEntry 11 }

pduEhandleUserPinMode OBJECT-TYPE
    SYNTAX INTEGER
        {
            visible(1),
            hidden (2)
        }
    MAX-ACCESS read-write
    STATUS current
    DESCRIPTION
        "Rack MAX-ACCESS User PIN mode setting"
    ::= { pduEhandleEntry 12 }

pduEhandleAisleControl OBJECT-TYPE
    SYNTAX INTEGER
        {
            combined (1),
            standalone(2)
        }
    MAX-ACCESS read-write
    STATUS current
    DESCRIPTION
        "Rack MAX-ACCESS Aisle Control setting,
         when set to standalone each aisle will controlled seprately,
         when set to combined opposite aisle can be controlled with authenticated control action on either aisle"
    ::= { pduEhandleEntry 13 }


--     ======Hid hid control table==========
pduEhandleControlTable OBJECT-TYPE
    SYNTAX SEQUENCE OF PduEhandleControlEntry
    MAX-ACCESS not-accessible
    STATUS current
    DESCRIPTION
        "A list of smartcard.  The number of entries are
         given by number of pdu and pduEhandleCount."
    ::= { pduEhandle 2 }

pduEhandleControlEntry OBJECT-TYPE
    SYNTAX PduEhandleControlEntry
    MAX-ACCESS not-accessible
    STATUS current
    DESCRIPTION
        "The smart card table entry containing the usrname, cardid, cardaisle etc."
    INDEX { pduEhandleControlIndex }
    ::= { pduEhandleControlTable 1 }

PduEhandleControlEntry ::= SEQUENCE
    {
        pduEhandleControlIndex                    INTEGER,
        pduEhandleControlUserName                 DisplayString,
        pduEhandleControlCardIdStr                DisplayString,
        pduEhandleControlTimestamp                DisplayString,
        pduEhandleControlCardAisle                INTEGER,
        pduEhandleControlStartTime                DisplayString,
        pduEhandleControlExpireTime               DisplayString,
        pduEhandleControlTempUser                 INTEGER,
        pduEhandleControlPin                      DisplayString
    }

pduEhandleControlIndex OBJECT-TYPE
    SYNTAX INTEGER (1..200)
    MAX-ACCESS read-only
    STATUS current
    DESCRIPTION
        "The index of the PDU smartcard table entry"
    ::= { pduEhandleControlEntry 1 }

pduEhandleControlUserName OBJECT-TYPE
    SYNTAX DisplayString
    MAX-ACCESS read-write
    STATUS current
    DESCRIPTION
        "User name of smartcard"
    ::= { pduEhandleControlEntry 2 }

-- pduEhandleControlCardID reads 0 in 1.5 series PDUs
-- keeping the OID for backward compatibility
pduEhandleControlCardIdStr	OBJECT-TYPE
    SYNTAX DisplayString
    MAX-ACCESS read-write
    STATUS current
    DESCRIPTION
        "smartcard ID."
    ::= { pduEhandleControlEntry 3 }

pduEhandleControlTimestamp OBJECT-TYPE
    SYNTAX DisplayString
    MAX-ACCESS read-only
    STATUS current
    DESCRIPTION
        "Indicates the date and time of accessing"
    ::= { pduEhandleControlEntry 4 }

pduEhandleControlCardAisle OBJECT-TYPE
    SYNTAX INTEGER
        {
            hot(1),
            cold(2),
            both (3)
        }
    MAX-ACCESS read-write
    STATUS current
    DESCRIPTION
        "Aisle of authorized card"
    ::= { pduEhandleControlEntry 5 }

pduEhandleControlStartTime OBJECT-TYPE
    SYNTAX DisplayString
    MAX-ACCESS read-write
    STATUS current
    DESCRIPTION
        "Indicates the start date and time Rack MAX-ACCESS user is given access"
    ::= { pduEhandleControlEntry 6 }

pduEhandleControlExpireTime OBJECT-TYPE
    SYNTAX DisplayString
    MAX-ACCESS read-write
    STATUS current
    DESCRIPTION
        "Indicates the date and time when the MAX-ACCESS of user card will expire, To set expire time first set user as temporary user"
    ::= { pduEhandleControlEntry 7 }

pduEhandleControlTempUser OBJECT-TYPE
    SYNTAX INTEGER
        {
            no(1),
            yes(2)
        }
    MAX-ACCESS read-write
    STATUS current
    DESCRIPTION
        "Indicates if the card user has temporary access"
    ::= { pduEhandleControlEntry 8 }

pduEhandleControlPin OBJECT-TYPE
    SYNTAX DisplayString
    MAX-ACCESS read-write
    STATUS current
    DESCRIPTION
        "Rack acess control entry keypad PIN"
    ::= { pduEhandleControlEntry 9 }

esp  						OBJECT IDENTIFIER ::= { enlogic 2 }
espNamePlate  					OBJECT IDENTIFIER ::= { esp 1 }
espUnit  					OBJECT IDENTIFIER ::= { esp 2 }
espInputPhase  					OBJECT IDENTIFIER ::= { esp 3 }
espCircuitBreaker  				OBJECT IDENTIFIER ::= { esp 4 }
espExternalSensor  				OBJECT IDENTIFIER ::= { esp 6 }
espTraps						OBJECT IDENTIFIER ::= { esp 9 }

-- Start espNamePlate

-- espNamePlateTable
espNamePlateTable  OBJECT-TYPE
	SYNTAX SEQUENCE OF EspNamePlateEntry
	MAX-ACCESS  	not-accessible
	STATUS 	current
	DESCRIPTION 
		"A table of es PDU nameplate data"
	::= { espNamePlate 2 }
	
espNamePlateEntry  OBJECT-TYPE
	SYNTAX 	EspNamePlateEntry
	MAX-ACCESS  	not-accessible
	STATUS 	current
	DESCRIPTION 
		"Nameplate data from the PDU being queried. The numbers of entries equals the value of espNamePlateTableSize."
	INDEX { espNamePlateIndex }
	::= { espNamePlateTable 1 }

EspNamePlateEntry ::= SEQUENCE {
	espNamePlateIndex
		Integer32,
	espNamePlateName
		DisplayString,
	espNamePlateLocation
		DisplayString,
	espNamePlateInetAddressType
		InetAddressType,
	espNamePlateIPAddress
		InetAddress,
	espNamePlateInetNetMask
		InetAddress,
	espNamePlateInetGateway
		InetAddress,
	espNamePlateMACAddress
		MacAddress,
	espNamePlateUTCTimeOffset
		DisplayString,
	espNamePlateModelNumber
		DisplayString,
	espNamePlateSerialNumber
		DisplayString,
	espNamePlateDateofManufacture
		DisplayString,
	espNamePlateFirmwareVersion
		DisplayString,
	espNamePlateFirmwareVersionTimeStamp
		DisplayString,
	espNamePlateType
		INTEGER
	}

espNamePlateIndex  OBJECT-TYPE
	SYNTAX 	INTEGER(1..256)
	MAX-ACCESS  	not-accessible
	STATUS 	current
	DESCRIPTION 
		"The index of the es PDU nameplate table entry"
	::= { espNamePlateEntry 1 }
	
espNamePlateName  OBJECT-TYPE
	SYNTAX 	DisplayString
	MAX-ACCESS  	read-only
	STATUS 	current
	DESCRIPTION 
		"A user-defined string identifying the es PDU"
	::= { espNamePlateEntry 2 }
	
espNamePlateLocation  OBJECT-TYPE
	SYNTAX 	DisplayString
	MAX-ACCESS  	read-only
	STATUS 	current
	DESCRIPTION 
		"A user-defined string identifying the location of PDU"
	::= { espNamePlateEntry 3 }

espNamePlateInetAddressType  OBJECT-TYPE
	SYNTAX 	InetAddressType
	MAX-ACCESS  	read-only
	STATUS 	current
	DESCRIPTION 
		"The type of address format"
	::= { espNamePlateEntry 4 }

espNamePlateIPAddress  OBJECT-TYPE
	SYNTAX 	InetAddress
	MAX-ACCESS  	read-only
	STATUS 	current
	DESCRIPTION 
		"The current IP address. A value of 0.0.0.0 indicates an error or an unset option"
	::= { espNamePlateEntry 5 }
	
espNamePlateInetNetMask  OBJECT-TYPE
	SYNTAX 	InetAddress
	MAX-ACCESS  	read-only
	STATUS 	current
	DESCRIPTION 
		"The current netmask. A value of 0.0.0.0 indiates an error or an unset option"
	::= { espNamePlateEntry 6 }
	
espNamePlateInetGateway  OBJECT-TYPE
	SYNTAX 	InetAddress
	MAX-ACCESS  	read-only
	STATUS 	current
	DESCRIPTION 
		"The current gateway. A value of 0.0.0.0 indicates an error or an unset option"
	::= { espNamePlateEntry 7 }
	
espNamePlateMACAddress  OBJECT-TYPE
	SYNTAX 	MacAddress
	MAX-ACCESS  	read-only
	STATUS 	current
	DESCRIPTION 
		"The assigned MAC address for the PDU"
	::= { espNamePlateEntry 8 }
	
espNamePlateUTCTimeOffset  OBJECT-TYPE
	SYNTAX 	DisplayString
	MAX-ACCESS  	read-only
	STATUS 	current
	DESCRIPTION 
		"The difference in hours and minutes from Coordinated Universal 
		Time(UTC) for the time used in a particular time zone"
	::= { espNamePlateEntry 9 }
	
espNamePlateModelNumber  OBJECT-TYPE
	SYNTAX 	DisplayString
	MAX-ACCESS  	read-only
	STATUS 	current
	DESCRIPTION 
		"The PDU model number"
	::= { espNamePlateEntry 10 }
	
espNamePlateSerialNumber  OBJECT-TYPE
	SYNTAX 	DisplayString
	MAX-ACCESS  	read-only
	STATUS 	current
	DESCRIPTION 
		"The PDU serial number"
	::= { espNamePlateEntry 11 }
	
espNamePlateDateofManufacture  OBJECT-TYPE
	SYNTAX 	DisplayString
	MAX-ACCESS  	read-only
	STATUS 	current
	DESCRIPTION 
		"The date the PDU was manufactured in mm/dd/yyyy format"
	::= { espNamePlateEntry 12 }

espNamePlateFirmwareVersion  OBJECT-TYPE
	SYNTAX 	DisplayString
	MAX-ACCESS  	read-only
	STATUS 	current
	DESCRIPTION 
		"The PDU firmware version"
	::= { espNamePlateEntry 13 }
	
espNamePlateFirmwareVersionTimeStamp  OBJECT-TYPE
	SYNTAX 	DisplayString
	MAX-ACCESS  	read-only
	STATUS 	current
	DESCRIPTION 
		"Timestamp of when the PDU firmware was last updated"
	::= { espNamePlateEntry 14 }
	
espNamePlateType  OBJECT-TYPE
	SYNTAX 	INTEGER {
		pdu (0),
		inlineMeter (1)
	}
	MAX-ACCESS  	read-only
	STATUS 	current
	DESCRIPTION 
		"The type of Unit, PDU or Inline Meter"
	::= { espNamePlateEntry 15 }
	
	
-- Start espUnit

espUnitConfigTable  OBJECT-TYPE
	SYNTAX SEQUENCE OF EspUnitConfigEntry
	MAX-ACCESS  	not-accessible
	STATUS 	current
	DESCRIPTION 
		"A table of PDU configuration data"
	::= { espUnit 2 }
	
espUnitConfigEntry  OBJECT-TYPE
	SYNTAX 	EspUnitConfigEntry
	MAX-ACCESS  	not-accessible
	STATUS 	current
	DESCRIPTION 
		"Configuration data from the PDU being queried. The number of entries equals the value of espUnitTableSize"
	INDEX { espUnitConfigIndex }
	::= { espUnitConfigTable 1 }

EspUnitConfigEntry ::= SEQUENCE {
	espUnitConfigIndex
		Integer32,
	espUnitConfigName
		DisplayString,
	espUnitConfigLocation
		DisplayString,
	espUnitConfigEnergyReset
		INTEGER,
	espUnitConfigResetNetworkManagementCard
		INTEGER
	}

espUnitConfigIndex  OBJECT-TYPE
	SYNTAX 	INTEGER(1..256)
	MAX-ACCESS  	not-accessible
	STATUS 	current
	DESCRIPTION 
		"The index of the PDU Unit Config Entry"
	::= { espUnitConfigEntry 1 }
	
espUnitConfigName  OBJECT-TYPE
	SYNTAX 	DisplayString
	MAX-ACCESS  	read-write
	STATUS 	current
	DESCRIPTION 
		"A user-defined string identifying the PDU"
	::= { espUnitConfigEntry 2 }
	
espUnitConfigLocation  OBJECT-TYPE
	SYNTAX 	DisplayString
	MAX-ACCESS  	read-write
	STATUS 	current
	DESCRIPTION 
		"A user-defined string identifying the location of the PDU"
	::= { espUnitConfigEntry 3 }
	
espUnitConfigEnergyReset  OBJECT-TYPE
	SYNTAX 	INTEGER {
		noOperation (1),
		reset (2),
		notSupported (3)
	}
	MAX-ACCESS  	read-write
	STATUS 	current
	DESCRIPTION 
		"Setting this OID to reset (2) will cause the device energy meter value 
		to be reset to zero. Getting this OID in models that support this 
		feature will do nothing and return the noOperation(1) value. Models 
		that do not support this feature will respond to this OID with a 
		value of notSupported (3). Attempts to set this OID in these models will fail. "
	::= { espUnitConfigEntry 15 }

espUnitConfigResetNetworkManagementCard  OBJECT-TYPE
	SYNTAX 	INTEGER {
		noOperation (0),
		reset (1)
	}
	MAX-ACCESS  	read-write
	STATUS 	current
	DESCRIPTION 
		"Getting this OID will return noOperation(0). Setting this OID to reset(1) will reset NMC."
	::= { espUnitConfigEntry 20 }
	
espUnitPropertiesTable  OBJECT-TYPE
	SYNTAX SEQUENCE OF EspUnitPropertiesEntry
	MAX-ACCESS  	not-accessible
	STATUS 	current
	DESCRIPTION 
		"A table of PDU properties"
	::= { espUnit 3 }
	
espUnitPropertiesEntry  OBJECT-TYPE
	SYNTAX 	EspUnitPropertiesEntry
	MAX-ACCESS  	not-accessible
	STATUS 	current
	DESCRIPTION 
		"A unit properties entry containing objects for a particular unit."
	INDEX { espUnitPropertiesIndex }
	::= { espUnitPropertiesTable 1 }

EspUnitPropertiesEntry ::= SEQUENCE {
	espUnitPropertiesIndex
		Integer32,
	espUnitPropertiesName
		DisplayString,
	espUnitPropertiesOutletCount
		Integer32,
	espUnitPropertiesSwitchedOutletCount
		Integer32,
	espUnitPropertiesMeteredOutletCount
		Integer32,
	espUnitPropertiesInputPhaseCount
		Integer32,
	espUnitPropertiesCircuitBreakerCount
		Integer32,
	espUnitPropertiesMaxExternalSensorCount
		Integer32,
	espUnitPropertiesConnExternalSensorCount
		Integer32,
	espUnitPropertiesRatedVoltage
		DisplayString,
	espUnitPropertiesRatedMaxCurrent
		DisplayString,
	espUnitPropertiesRatedFrequency
		DisplayString,
	espUnitPropertiesRatedPower
		DisplayString
	}

espUnitPropertiesIndex  OBJECT-TYPE
	SYNTAX 	INTEGER(1..256)
	MAX-ACCESS  	not-accessible
	STATUS 	current
	DESCRIPTION 
		"The index of the PDU properties table entry"
	::= { espUnitPropertiesEntry 1 }
	
espUnitPropertiesName  OBJECT-TYPE
	SYNTAX 	DisplayString
	MAX-ACCESS  	read-only
	STATUS 	current
	DESCRIPTION 
		"A user-defined string identifying the PDU"
	::= { espUnitPropertiesEntry 2 }
	
espUnitPropertiesOutletCount  OBJECT-TYPE
	SYNTAX 	INTEGER(1..256)
	MAX-ACCESS  	read-only
	STATUS 	current
	DESCRIPTION 
		"The total number of outlets on the PDU"
	::= { espUnitPropertiesEntry 3 }
	
espUnitPropertiesSwitchedOutletCount  OBJECT-TYPE
	SYNTAX 	INTEGER(1..256)
	MAX-ACCESS  	read-only
	STATUS 	current
	DESCRIPTION 
		"The total number of switched outlets on the PDU"
	::= { espUnitPropertiesEntry 4 }
	
espUnitPropertiesMeteredOutletCount  OBJECT-TYPE
	SYNTAX 	INTEGER(1..256)
	MAX-ACCESS  	read-only
	STATUS 	current
	DESCRIPTION 
		"The total number of metered outlets on the PDU"
	::= { espUnitPropertiesEntry 5 }
	
espUnitPropertiesInputPhaseCount  OBJECT-TYPE
	SYNTAX 	INTEGER(1..256)
	MAX-ACCESS  	read-only
	STATUS 	current
	DESCRIPTION 
		"The total number of phases on the PDU"
	::= { espUnitPropertiesEntry 6 }

espUnitPropertiesCircuitBreakerCount  OBJECT-TYPE
	SYNTAX 	INTEGER(0..255)
	MAX-ACCESS  	read-only
	STATUS 	current
	DESCRIPTION 
		"The total number of circuit breaker on the PDU"
	::= { espUnitPropertiesEntry 7 }
	
espUnitPropertiesMaxExternalSensorCount  OBJECT-TYPE
	SYNTAX 	INTEGER(0..255)
	MAX-ACCESS  	read-only
	STATUS 	current
	DESCRIPTION 
		"The maximum number of external sensors that can be connected to the PDU"
	::= { espUnitPropertiesEntry 8 }
	
espUnitPropertiesConnExternalSensorCount  OBJECT-TYPE
	SYNTAX 	INTEGER(0..255)
	MAX-ACCESS  	read-only
	STATUS 	current
	DESCRIPTION 
		"The current number of external sensors connected to the PDU"
	::= { espUnitPropertiesEntry 9 }
	
espUnitPropertiesRatedVoltage  OBJECT-TYPE
	SYNTAX 	DisplayString
	MAX-ACCESS  	read-only
	STATUS 	current
	DESCRIPTION 
		"The PDU voltage rating in Volts"
	::= { espUnitPropertiesEntry 10 }
	
espUnitPropertiesRatedMaxCurrent  OBJECT-TYPE
	SYNTAX 	DisplayString
	MAX-ACCESS  	read-only
	STATUS 	current
	DESCRIPTION 
		"The PDU current rating in Amps"
	::= { espUnitPropertiesEntry 11 }
	
espUnitPropertiesRatedFrequency  OBJECT-TYPE
	SYNTAX 	DisplayString
	MAX-ACCESS  	read-only
	STATUS 	current
	DESCRIPTION 
		"The PDU frequency rating in Hz"
	::= { espUnitPropertiesEntry 12 }
	
espUnitPropertiesRatedPower  OBJECT-TYPE
	SYNTAX 	DisplayString
	MAX-ACCESS  	read-only
	STATUS 	current
	DESCRIPTION 
		"The PDU VA (VoltAmps) rating."
	::= { espUnitPropertiesEntry 13 }
	
espUnitSTATUSTable  OBJECT-TYPE
	SYNTAX SEQUENCE OF EspUnitSTATUSEntry
	MAX-ACCESS  	not-accessible
	STATUS 	current
	DESCRIPTION 
		"A table of PDU STATUS information"
	::= { espUnit 4 }
	
espUnitSTATUSEntry  OBJECT-TYPE
	SYNTAX 	EspUnitSTATUSEntry
	MAX-ACCESS  	not-accessible
	STATUS 	current
	DESCRIPTION 
		"STATUS information from the PDU being queried"
	INDEX { espUnitSTATUSIndex }
	::= { espUnitSTATUSTable 1 }

EspUnitSTATUSEntry ::= SEQUENCE {
	espUnitSTATUSIndex
		Integer32,
	espUnitSTATUSName
		DisplayString,
	espUnitSTATUSLoadState
		INTEGER,
	espUnitSTATUSActivePower
		Integer32,
	espUnitSTATUSApparentPower
		Integer32,
	espUnitSTATUSEnergy
		Integer32,
	espUnitSTATUSResettableEnergy
		Integer32,
	espUnitSTATUSEnergyStartTime
		DisplayString
	}

espUnitSTATUSIndex  OBJECT-TYPE
	SYNTAX 	INTEGER(1..256)
	MAX-ACCESS  	not-accessible
	STATUS 	current
	DESCRIPTION 
		"The index of the PDU STATUS table entry"
	::= { espUnitSTATUSEntry 1 }
	
espUnitSTATUSName  OBJECT-TYPE
	SYNTAX 	DisplayString
	MAX-ACCESS  	read-only
	STATUS 	current
	DESCRIPTION 
		"A user-defined string identifying the PDU"
	::= { espUnitSTATUSEntry 2 }
	
espUnitSTATUSLoadState  OBJECT-TYPE
	SYNTAX 	INTEGER {
		upperCritical (1),
		upperWarning (2),
		lowerWarning (3),
		lowerCritical (4),
		normal (5)
	}
	MAX-ACCESS  	read-only
	STATUS 	current
	DESCRIPTION 
		"Returns the present load STATUS of the PDU based on Active Power."
	::= { espUnitSTATUSEntry 3 }
	
espUnitSTATUSActivePower  OBJECT-TYPE
	SYNTAX 	Integer32
	MAX-ACCESS  	read-only
	STATUS 	current
	DESCRIPTION 
		"Returns power consumption, in Watts(W), 
		of the PDU being queried."
	::= { espUnitSTATUSEntry 4 }

espUnitSTATUSApparentPower  OBJECT-TYPE
	SYNTAX 	Integer32
	MAX-ACCESS  	read-only
	STATUS 	current
	DESCRIPTION 
		"Returns power consumption, in Volt-Amps(VA) 
		of the PDU load being queried."
	::= { espUnitSTATUSEntry 5 }
	
espUnitSTATUSEnergy  OBJECT-TYPE
	SYNTAX 	Integer32
	MAX-ACCESS  	read-only
	STATUS 	current
	DESCRIPTION 
		"Returns total energy consumed, in tenths of Kilowatt-Hours(kWh), of the PDU over its lifetime."		
	::= { espUnitSTATUSEntry 9 }

espUnitSTATUSResettableEnergy  OBJECT-TYPE
	SYNTAX 	Integer32
	MAX-ACCESS  	read-only
	STATUS 	current
	DESCRIPTION 
		"A user resettable energy meter measuring PDU energy consumption 
		in tenths of kilowatt-hours(kWh)."
	::= { espUnitSTATUSEntry 10 }
	
espUnitSTATUSEnergyStartTime  OBJECT-TYPE
	SYNTAX 	DisplayString
	MAX-ACCESS  	read-only
	STATUS 	current
	DESCRIPTION 
		"Indicates the date and time of the last device energy meter reset"
	::= { espUnitSTATUSEntry 11 }
	

-- Start espInputPhase
espInputPhaseConfigTable  OBJECT-TYPE
	SYNTAX SEQUENCE OF EspInputPhaseConfigEntry
	MAX-ACCESS  	not-accessible
	STATUS 	current
	DESCRIPTION 
		"A table of PDU Input Phase configuration data"
	::= { espInputPhase 2 }
	
espInputPhaseConfigEntry  OBJECT-TYPE
	SYNTAX 	EspInputPhaseConfigEntry
	MAX-ACCESS  	not-accessible
	STATUS 	current
	DESCRIPTION 
		"An input phase entry containing objects for a particular input phase."
	INDEX { espUnitConfigIndex, espInputPhaseConfigIndex }
	::= { espInputPhaseConfigTable 1 }

EspInputPhaseConfigEntry ::= SEQUENCE {
	espInputPhaseConfigIndex
		Integer32,
	espInputPhaseConfigCount
		Integer32
	}

espInputPhaseConfigIndex  OBJECT-TYPE
	SYNTAX 	INTEGER(1..256)
	MAX-ACCESS  	not-accessible
	STATUS 	current
	DESCRIPTION 
		"The index of the PDU Input Phase configuration table entry"
	::= { espInputPhaseConfigEntry 1 }
	
espInputPhaseConfigCount  OBJECT-TYPE
	SYNTAX 	INTEGER(1..256)
	MAX-ACCESS  	read-only
	STATUS 	current
	DESCRIPTION 
		"The total number of Input Phases"
	::= { espInputPhaseConfigEntry 2 }
			
espInputPhaseSTATUSTable  OBJECT-TYPE
	SYNTAX SEQUENCE OF EspInputPhaseSTATUSEntry
	MAX-ACCESS  	not-accessible
	STATUS 	current
	DESCRIPTION 
		"A table of PDU Input Phase STATUS data"
	::= { espInputPhase 4 }
	
espInputPhaseSTATUSEntry  OBJECT-TYPE
	SYNTAX 	EspInputPhaseSTATUSEntry
	MAX-ACCESS  	not-accessible
	STATUS 	current
	DESCRIPTION 
		"An input phase STATUS entry containing objects for a particular input phase."
	INDEX { espUnitSTATUSIndex, espInputPhaseSTATUSIndex }
	::= { espInputPhaseSTATUSTable 1 }

EspInputPhaseSTATUSEntry ::= SEQUENCE {
	espInputPhaseSTATUSIndex
		Integer32,
	espInputPhaseSTATUSCount
		Integer32,
	espInputPhaseSTATUSCurrentState
		INTEGER,
	espInputPhaseSTATUSVoltageState
		INTEGER,
	espInputPhaseSTATUSCurrent
		Integer32,
	espInputPhaseSTATUSVoltage
		Integer32,
	espInputPhaseSTATUSActivePower
		Integer32,
	espInputPhaseSTATUSApparentPower
		Integer32,
	espInputPhaseSTATUSPowerFactor
		Integer32
	}

espInputPhaseSTATUSIndex  OBJECT-TYPE
	SYNTAX 	INTEGER(1..256)
	MAX-ACCESS  	not-accessible
	STATUS 	current
	DESCRIPTION 
		"The index of the PDU Input Phase STATUS entry"
	::= { espInputPhaseSTATUSEntry 1 }
	
espInputPhaseSTATUSCount  OBJECT-TYPE
	SYNTAX 	INTEGER(1..256)
	MAX-ACCESS  	read-only
	STATUS 	current
	DESCRIPTION 
		"The numeric Input Phase ID"
	::= { espInputPhaseSTATUSEntry 2 }
	
espInputPhaseSTATUSCurrentState  OBJECT-TYPE
	SYNTAX 	INTEGER {
		upperCritical (1),
		upperWarning (2),
		lowerWarning (3),
		lowerCritical (4),
		normal (5)
	}
	MAX-ACCESS  	read-only
	STATUS 	current
	DESCRIPTION 
		"Indicates the present current STATUS of the PDU Input Phase being queried"
	::= { espInputPhaseSTATUSEntry 3 }
	
espInputPhaseSTATUSVoltageState  OBJECT-TYPE
	SYNTAX 	INTEGER {
		upperCritical (1),
		upperWarning (2),
		lowerWarning (3),
		lowerCritical (4),
		normal (5)
	}
	MAX-ACCESS  	read-only
	STATUS 	current
	DESCRIPTION 
		"Indicates the present voltage STATUS of the PDU Input Phase being queried"
	::= { espInputPhaseSTATUSEntry 4 }
	
espInputPhaseSTATUSCurrent  OBJECT-TYPE
	SYNTAX 	Integer32
	MAX-ACCESS  	read-only
	STATUS 	current
	DESCRIPTION 
		"Returns the current draw, in hundredths of Amps(A), of the load on the 
		PDU Input Phase being queried."
	::= { espInputPhaseSTATUSEntry 5 }
	
espInputPhaseSTATUSVoltage  OBJECT-TYPE
	SYNTAX 	Integer32
	MAX-ACCESS  	read-only
	STATUS 	current
	DESCRIPTION 
		"Returns the voltage, in Volts(V), of the PDU Input Phase being queried."
	::= { espInputPhaseSTATUSEntry 6 }
	
espInputPhaseSTATUSActivePower  OBJECT-TYPE
	SYNTAX 	Integer32
	MAX-ACCESS  	read-only
	STATUS 	current
	DESCRIPTION 
		"Returns power consumption, in Watts(W), 
		consumed on the PDU Input Phase being queried."
	::= { espInputPhaseSTATUSEntry 7 }
	
espInputPhaseSTATUSApparentPower  OBJECT-TYPE
	SYNTAX 	Integer32
	MAX-ACCESS  	read-only
	STATUS 	current
	DESCRIPTION 
		"Returns power consumption, in Volt-Amps(VA), 
		of the PDU Input Phase being queried."
	::= { espInputPhaseSTATUSEntry 8 }
	
espInputPhaseSTATUSPowerFactor  OBJECT-TYPE
	SYNTAX 	Integer32
	MAX-ACCESS  	read-only
	STATUS 	current
	DESCRIPTION 
		"Returns the ratio of active to apparent power of the PDU Input Phase being queried."
	::= { espInputPhaseSTATUSEntry 9 }

-- Start espCircuitBreaker
espCircuitBreakerConfigTable  OBJECT-TYPE
	SYNTAX SEQUENCE OF EspCircuitBreakerConfigEntry
	MAX-ACCESS  	not-accessible
	STATUS 	current
	DESCRIPTION 
		"A table of PDU Circuit Breaker configuration data"
	::= { espCircuitBreaker 2 }
	
espCircuitBreakerConfigEntry  OBJECT-TYPE
	SYNTAX 	EspCircuitBreakerConfigEntry
	MAX-ACCESS  	not-accessible
	STATUS 	current
	DESCRIPTION 
		"A circuit breaker configuration entry containing objects for a particular circuit breaker."
	INDEX { espUnitConfigIndex, espCircuitBreakerConfigIndex }
	::= { espCircuitBreakerConfigTable 1 }

EspCircuitBreakerConfigEntry ::= SEQUENCE {
	espCircuitBreakerConfigIndex
		Integer32,
	espCircuitBreakerConfigCount
		Integer32,
	espCircuitBreakerName
		DisplayString
	}

espCircuitBreakerConfigIndex  OBJECT-TYPE
	SYNTAX 	INTEGER(1..256)
	MAX-ACCESS  	not-accessible
	STATUS 	current
	DESCRIPTION 
		"The index of the PDU Circuit Breaker configuration table entry"
	::= { espCircuitBreakerConfigEntry 1 }
	
espCircuitBreakerConfigCount  OBJECT-TYPE
	SYNTAX 	INTEGER(0..255)
	MAX-ACCESS  	read-only
	STATUS 	current
	DESCRIPTION 
		"The number of circuit breakers on the PDU"
	::= { espCircuitBreakerConfigEntry 2 }
	
espCircuitBreakerName  OBJECT-TYPE
	SYNTAX 	DisplayString
	MAX-ACCESS  	read-only
	STATUS 	current
	DESCRIPTION 
		"The label of the circuit breaker"
	::= { espCircuitBreakerConfigEntry 3 }
	
espCircuitBreakerPropertiesTable  OBJECT-TYPE
	SYNTAX SEQUENCE OF EspCircuitBreakerPropertiesEntry
	MAX-ACCESS  	not-accessible
	STATUS 	current
	DESCRIPTION 
		"A table of PDU circuit breaker properties"
	::= { espCircuitBreaker 3 }

espCircuitBreakerPropertiesEntry  OBJECT-TYPE
	SYNTAX 	EspCircuitBreakerPropertiesEntry
	MAX-ACCESS  	not-accessible
	STATUS 	current
	DESCRIPTION 
		"A circuit breaker properties entry containing objects for a particular circuit breaker."
	INDEX { espUnitPropertiesIndex, espCircuitBreakerPropertiesIndex }
	::= { espCircuitBreakerPropertiesTable 1 }

EspCircuitBreakerPropertiesEntry ::= SEQUENCE {
	espCircuitBreakerPropertiesIndex
		Integer32,
	espCircuitBreakerPropertiesCount
		Integer32,
	espCircuitBreakerPropertiesInputLayout
		INTEGER
	}

espCircuitBreakerPropertiesIndex  OBJECT-TYPE
	SYNTAX 	INTEGER(1..256)
	MAX-ACCESS  	not-accessible
	STATUS 	current
	DESCRIPTION 
		"The index of the PDU Circuit Breaker properties table entry"
	::= { espCircuitBreakerPropertiesEntry 1 }
	
espCircuitBreakerPropertiesCount  OBJECT-TYPE
	SYNTAX 	INTEGER(0..255)
	MAX-ACCESS  	read-only
	STATUS 	current
	DESCRIPTION 
		"The number of Circuit Breakers"
	::= { espCircuitBreakerPropertiesEntry 2 }
	
espCircuitBreakerPropertiesInputLayout  OBJECT-TYPE
	SYNTAX 	INTEGER {
		seqPhase1ToNeutral (1),
		seqPhase2ToNeutral (2),
		seqPhase3ToNeutral (3),
		seqPhase1ToPhase2 (4),
		seqPhase2ToPhase3 (5),
		seqPhase3ToPhase1 (6)
	}
	MAX-ACCESS  	read-only
	STATUS 	current
	DESCRIPTION 
		"This OID describes the outlet phase connections on 
		the referenced bank as follows: 
		seqPhase1ToNeutral(1) indicates that outlets attached 
		to circuit breaker are connected from Phase 1 to Neutral. 
		seqPhase2ToNeutral(2) indicates that outlets attached 
		to circuit breaker are connected from Phase 2 to Neutral. 
		seqPhase3ToNeutral(3) indicates that outlets attached 
		to circuit breaker are connected from Phase 3 to Neutral. 
		seqPhase1ToPhase2(4) indicates that outlets attached 
		to circuit breaker are connected from Phase 1 to Phase2. 
		seqPhase2ToPhase3(5) indicates that outlets attached 
		to circuit breaker are connected from Phase 2 to Phase3.  
		seqPhase3ToPhase1(6) indicates that outlets attached 
		to circuit breaker are connected from Phase 3 to Phase1. "
	::= { espCircuitBreakerPropertiesEntry 3 }
	
espCircuitBreakerSTATUSTable  OBJECT-TYPE
	SYNTAX SEQUENCE OF EspCircuitBreakerSTATUSEntry
	MAX-ACCESS  	not-accessible
	STATUS 	current
	DESCRIPTION 
		"A table of PDU circuit breaker STATUS data"
	::= { espCircuitBreaker 4 }
	
espCircuitBreakerSTATUSEntry  OBJECT-TYPE
	SYNTAX 	EspCircuitBreakerSTATUSEntry
	MAX-ACCESS  	not-accessible
	STATUS 	current
	DESCRIPTION 
		"A circuit breaker STATUS entry containing objects for a particular circuit breaker."
	INDEX { espUnitSTATUSIndex, espCircuitBreakerSTATUSIndex }
	::= { espCircuitBreakerSTATUSTable 1 }

EspCircuitBreakerSTATUSEntry ::= SEQUENCE {
	espCircuitBreakerSTATUSIndex
		Integer32,
	espCircuitBreakerSTATUSCount
		Integer32,
	espCircuitBreakerLabel
		DisplayString,
	espCircuitBreakerSTATUSLoadState
		INTEGER,
	espCircuitBreakerSTATUSCurrent
		Integer32
	}

espCircuitBreakerSTATUSIndex  OBJECT-TYPE
	SYNTAX 	INTEGER(1..256)
	MAX-ACCESS  	not-accessible
	STATUS 	current
	DESCRIPTION 
		"The index of the PDU Circuit Breaker STATUS table entry"
	::= { espCircuitBreakerSTATUSEntry 1 }
	
espCircuitBreakerSTATUSCount  OBJECT-TYPE
	SYNTAX 	INTEGER(0..255)
	MAX-ACCESS  	read-only
	STATUS 	current
	DESCRIPTION 
		"The number of Circuit Breakers"
	::= { espCircuitBreakerSTATUSEntry 2 }
	
espCircuitBreakerLabel  OBJECT-TYPE
	SYNTAX 	DisplayString
	MAX-ACCESS  	read-only
	STATUS 	current
	DESCRIPTION 
		"The label on the PDU identifying the circuit breaker"
	::= { espCircuitBreakerSTATUSEntry 3 }
	
espCircuitBreakerSTATUSLoadState  OBJECT-TYPE
	SYNTAX 	INTEGER {
		upperCritical (1),
		upperWarning (2),
		lowerWarning (3),
		lowerCritical (4),
		normal (5),
		off (6)
	}
	MAX-ACCESS  	read-only
	STATUS 	current
	DESCRIPTION 
		"Indicates the present load STATUS of the PDU Circuit 
		Breaker being queried"
	::= { espCircuitBreakerSTATUSEntry 4 }
	
espCircuitBreakerSTATUSCurrent  OBJECT-TYPE
	SYNTAX 	Integer32
	MAX-ACCESS  	read-only
	STATUS 	current
	DESCRIPTION 
		"Returns the current draw, in hundredths of Amps(A), of the load on 
		the PDU Circuit Breaker being queried."
	::= { espCircuitBreakerSTATUSEntry 5 }
	
-- Start espExternalSensor
espExternalSensorNamePlateTable  OBJECT-TYPE
	SYNTAX SEQUENCE OF EspExternalSensorNamePlateEntry
	MAX-ACCESS  	not-accessible
	STATUS 	current
	DESCRIPTION 
		"A table of PDU ExternalSensorNamePlate data"
	::= { espExternalSensor 2 }

espExternalSensorNamePlateEntry  OBJECT-TYPE
	SYNTAX 	EspExternalSensorNamePlateEntry
	MAX-ACCESS  	not-accessible
	STATUS 	current
	DESCRIPTION 
		"External Sensor Name Plate data from the external 
		sensor being queried. The number of entries equals 
		the value of espExternalSensorNamePlateTableSize."
	INDEX { espNamePlateIndex, espExternalSensorNamePlateIndex }
	::= { espExternalSensorNamePlateTable 1 }

EspExternalSensorNamePlateEntry ::= SEQUENCE {
	espExternalSensorNamePlateIndex
		Integer32,
	espExternalSensorNamePlateName
		DisplayString,
	espExternalSensorNamePlateSerialNumber
		DisplayString,
	espExternalSensorNamePlateType
		INTEGER,
	espExternalSensorNamePlateUnits
		INTEGER
	}

espExternalSensorNamePlateIndex  OBJECT-TYPE
	SYNTAX 	INTEGER(0..255)
	MAX-ACCESS  	not-accessible
	STATUS 	current
	DESCRIPTION 
		"The index of the PDU External Sensor STATUS table entry"
	::= { espExternalSensorNamePlateEntry 1 }

espExternalSensorNamePlateName  OBJECT-TYPE
	SYNTAX 	DisplayString
	MAX-ACCESS  	read-only
	STATUS 	current
	DESCRIPTION 
		"A user-defined string identifying the external sensor"
	::= { espExternalSensorNamePlateEntry 2 }

espExternalSensorNamePlateSerialNumber  OBJECT-TYPE
	SYNTAX 	DisplayString
	MAX-ACCESS  	read-only
	STATUS 	current
	DESCRIPTION 
		"The serial number of the external sensor being queried"
	::= { espExternalSensorNamePlateEntry 5 }

espExternalSensorNamePlateType  OBJECT-TYPE
	SYNTAX 	INTEGER {
		temperature (1),
		humidity (2),
		doorSwitch (3),
		dryContact (4),
		spotFluid (5),
		ropeFluid (6),
		smoke (7),
		beacon (8)
	}
	MAX-ACCESS  	read-only
	STATUS 	current
	DESCRIPTION 
		"The type of external sensor."
	::= { espExternalSensorNamePlateEntry 6 }

espExternalSensorNamePlateUnits  OBJECT-TYPE
	SYNTAX 	INTEGER {
		logic (0),
		degreeC (1),
		degreeF (2),
		percent (3)
	}
	MAX-ACCESS  	read-only
	STATUS 	current
	DESCRIPTION 
		"The base units the external sensor is measured in. 
		This parameter does not apply to onOff, trip, vibration,
		 waterDetection, smokeDetection sensors. "
	::= { espExternalSensorNamePlateEntry 7 }

espExternalSensorConfigTable  OBJECT-TYPE
	SYNTAX SEQUENCE OF EspExternalSensorConfigEntry
	MAX-ACCESS  	not-accessible
	STATUS 	current
	DESCRIPTION 
		"A table of PDU External Sensor configuration data"
	::= { espExternalSensor 3 }

espExternalSensorConfigEntry  OBJECT-TYPE
	SYNTAX 	EspExternalSensorConfigEntry
	MAX-ACCESS  	not-accessible
	STATUS 	current
	DESCRIPTION 
		"Configuration data from the PDU External 
		Sensor being queried"
	INDEX { espUnitConfigIndex, espExternalSensorConfigIndex }
	::= { espExternalSensorConfigTable 1 }

EspExternalSensorConfigEntry ::= SEQUENCE {
	espExternalSensorConfigIndex
		Integer32,
	espExternalSensorConfigAlarmState
		INTEGER
	}

espExternalSensorConfigIndex  OBJECT-TYPE
	SYNTAX 	INTEGER(0..255)
	MAX-ACCESS  	not-accessible
	STATUS 	current
	DESCRIPTION 
		"The index of the PDU External Sensor 
		configuration table entry"
	::= { espExternalSensorConfigEntry 1 }

espExternalSensorConfigAlarmState OBJECT-TYPE
	SYNTAX 	INTEGER {
		on (1),
		off (0)
	}
	MAX-ACCESS  	read-write
	STATUS 	current
	DESCRIPTION 
		"User defined alarm state of external sensor"
	::= { espExternalSensorConfigEntry 9 }
	
espExternalSensorSTATUSTable  OBJECT-TYPE
	SYNTAX SEQUENCE OF EspExternalSensorSTATUSEntry
	MAX-ACCESS  	not-accessible
	STATUS 	current
	DESCRIPTION 
		"A table of PDU External Sensor STATUS data"
	::= { espExternalSensor 4 }
	
espExternalSensorSTATUSEntry  OBJECT-TYPE
	SYNTAX 	EspExternalSensorSTATUSEntry
	MAX-ACCESS  	not-accessible
	STATUS 	current
	DESCRIPTION 
		"STATUS data from the PDU External Sensor 
		being queried"
	INDEX { espUnitSTATUSIndex, espExternalSensorSTATUSIndex }
	::= { espExternalSensorSTATUSTable 1 }

EspExternalSensorSTATUSEntry ::= SEQUENCE {
	espExternalSensorSTATUSIndex
		Integer32,
	espExternalSensorSTATUSName
		DisplayString,
	espExternalSensorSTATUSAisle
		INTEGER,
	espExternalSensorSTATUSCommSTATUS
		INTEGER,
	espExternalSensorSTATUSState
		INTEGER,
	espExternalSensorSTATUSValue
		Integer32,
	espExternalSensorSTATUSHighPrecisionValue
		Integer32
	}

espExternalSensorSTATUSIndex  OBJECT-TYPE
	SYNTAX 	INTEGER(0..255)
	MAX-ACCESS  	not-accessible
	STATUS 	current
	DESCRIPTION 
		"The index of the PDU External Sensor STATUS table entry"
	::= { espExternalSensorSTATUSEntry 1 }

espExternalSensorSTATUSName  OBJECT-TYPE
	SYNTAX 	DisplayString
	MAX-ACCESS  	read-only
	STATUS 	current
	DESCRIPTION 
		"The user-defined name for the External Sensor"
	::= { espExternalSensorSTATUSEntry 2 }

espExternalSensorSTATUSAisle  OBJECT-TYPE
	SYNTAX 	INTEGER {
		hotAisle (1),
		coldAisle (2)
	}
	MAX-ACCESS  	read-write
	STATUS 	current
	DESCRIPTION 
		"Indicates whether the external sensor is 
		in a hot or cold aisle"
	::= { espExternalSensorSTATUSEntry 3 }

espExternalSensorSTATUSCommSTATUS  OBJECT-TYPE
	SYNTAX 	INTEGER {
		notInstalled (1),
		commsOk (2),
		commsLost (3)
	}
	MAX-ACCESS  	read-only
	STATUS 	current
	DESCRIPTION 
		"The communications STATUS of the sensor"
	::= { espExternalSensorSTATUSEntry 4 }

espExternalSensorSTATUSState  OBJECT-TYPE
	SYNTAX 	INTEGER {
		notPresent (0), alarmed (1), normal (2), belowLowerCritical (3), belowLowerWarning (4), aboveUpperWarning (5), aboveUpperCritical (6)
	}
	MAX-ACCESS  	read-only
	STATUS 	current
	DESCRIPTION 
		"This OID reports the current state of the sensor. 
			A notPresent (0) response indicates that no sensor is attached.
			An alarmed (1) response indicates that the sensor is present 
			and its measured reading indicates alarmed.
			A normal (2) response indicates that the sensor is present 
			and its measured reading lies within all thresholds.
			A belowLowerCritical (3) response indicates that the sensor 
			is present and its measured reading lies below the lower critical threshold.
			A belowLowerWarning (4) response indicates that the sensor 
			is present and its measured reading lies below the lower warning threshold.
			An aboveUpperWarning (5) response indicates that the sensor 
			is present and its measured reading lies above the upper warning threshold.
			An aboveUpperCritical (6) response indicates that the sensor 
			is present and its measured reading lies above the upper critical threshold."
	::= { espExternalSensorSTATUSEntry 5 }

espExternalSensorSTATUSValue  OBJECT-TYPE
	SYNTAX 	Integer32
	MAX-ACCESS  	read-only
	STATUS 	current
	DESCRIPTION 
		"Sensor reading in espExternalSensorConfigUnits value."
	::= { espExternalSensorSTATUSEntry 6 }

espExternalSensorSTATUSHighPrecisionValue  OBJECT-TYPE
	SYNTAX 	Integer32
	MAX-ACCESS  	read-only
	STATUS 	current
	DESCRIPTION 
		"Temperature sensor reading in tenths of espExternalSensorConfigUnits value.
		This OID is applied to temperature sensor only"
	::= { espExternalSensorSTATUSEntry 8 }
	

-- Traps Information

espTrapsInfoIndex  OBJECT-TYPE
	SYNTAX 	INTEGER(1..256)
	MAX-ACCESS  	not-accessible
	STATUS 	current
	DESCRIPTION 
		"The index of the traps table entry"
	::= { espTraps 1 }


espUserName  OBJECT-TYPE
	SYNTAX 	DisplayString
	MAX-ACCESS  	read-only
	STATUS 	current
	DESCRIPTION 
		"The user currently logged in."
	::= { espTraps 2 }
	
espFirmwareVersion  OBJECT-TYPE
	SYNTAX 	DisplayString
	MAX-ACCESS  	read-only
	STATUS 	current
	DESCRIPTION 
		"The version of Firmware."
	::= { espTraps 4 }

espIndex  OBJECT-TYPE
	SYNTAX 	Integer32
	MAX-ACCESS  	accessible-for-notify
	STATUS 	current
	DESCRIPTION 
		"A unique value for PDU. Its value ranges between 1 
		and the value of PDU count"
	::= { espTraps 5 }

espExternalSensorIndex  OBJECT-TYPE
	SYNTAX 	Integer32
	MAX-ACCESS  	accessible-for-notify
	STATUS 	current
	DESCRIPTION 
		"A unique value for each sensor. Its value ranges between 1 
		and the value of external sensor count."
	::= { espTraps 6 }

espErrorDescription  OBJECT-TYPE
	SYNTAX 	DisplayString
	MAX-ACCESS  	accessible-for-notify
	STATUS 	current
	DESCRIPTION 
		"Description of the Error"
	::= { espTraps 7 }

espNetworkCardStart  		NOTIFICATION-TYPE
				OBJECTS {   espIndex,
						espNamePlateName,
			 		    espNamePlateInetAddressType,
					    espNamePlateIPAddress,
					    sysContact,
					    sysName,
					    sysLocation  }
				STATUS 	current
				DESCRIPTION 
					"The network card has started"
				::= { espTraps 8 }
	
espNetworkCardReset  		NOTIFICATION-TYPE
				OBJECTS {   espIndex,
						espNamePlateName,
			 		    userName,
					    espNamePlateInetAddressType,
					    espNamePlateIPAddress,
					    sysContact,
					    sysName,
					    sysLocation }
				STATUS 	current
				DESCRIPTION 
					"The network card was reset via the web or command line interface."
				::= { espTraps 9}	


espFirmwareUpdateCompleted  	NOTIFICATION-TYPE
				OBJECTS {   espIndex,
							espNamePlateName, 
    					    userName, 
					    espNamePlateInetAddressType,
					    espNamePlateIPAddress,
					    firmwareVersion,
    					    sysContact,
					    sysName,
					    sysLocation }
				STATUS 	current
				DESCRIPTION 
					"The firmware update has completed."
				::= { espTraps 10 }
	
espUserPasswordChange  		NOTIFICATION-TYPE
				OBJECTS {   espIndex,
							espNamePlateName, 
    					    userName, 
    				    	    espNamePlateInetAddressType,
					    espNamePlateIPAddress,
    					    userUpdated,
    					    sysContact,
					    sysName,
					    sysLocation }
				STATUS 	current
				DESCRIPTION 
					"A user password was changed. "
				::= { espTraps 11 }
	

espLogFileCleared  			NOTIFICATION-TYPE
				OBJECTS {   espIndex,
							espNamePlateName, 
    					    userName, 
					    espNamePlateInetAddressType,
					    espNamePlateIPAddress,
					    sysContact,
					    sysName,
					    sysLocation }
				STATUS 	current
				DESCRIPTION 
					"The log file has been cleared."
				::= { espTraps 12 }
	
espConfigurationFileExported  	NOTIFICATION-TYPE
				OBJECTS {   espIndex,
							espNamePlateName, 
    					    userName, 
					    espNamePlateInetAddressType,
					    espNamePlateIPAddress,
					    sysContact,
					    sysName,
					    sysLocation }
				STATUS 	current
				DESCRIPTION 
					"PDU configuration file was exported"
				::= { espTraps 13 }

espUnitActivePowerStateChange  NOTIFICATION-TYPE
				OBJECTS {   espIndex,
							espNamePlateName, 
    	  				    espNamePlateInetAddressType,
	  				    espNamePlateIPAddress,
	  				    espUnitSTATUSLoadState,
	  				    espUnitSTATUSActivePower,
	  				    sysContact,
	  				    sysName,
	  				    sysLocation }
				STATUS 	current
				DESCRIPTION 
					"PDU unit active power state changes."
				::= { espTraps 14 }
	
espInputphaseVoltageStateChange  	NOTIFICATION-TYPE
					OBJECTS {   espIndex,
								espNamePlateName, 
    	  					    espNamePlateInetAddressType,
	  					    espNamePlateIPAddress,
	  					    espInputPhaseSTATUSCount, 
	  					    espInputPhaseSTATUSVoltageState, 
	  					    espInputPhaseSTATUSVoltage,
	  					    sysContact,
	  					    sysName,
	  					    sysLocation }
					STATUS 	current
					DESCRIPTION 
						"PDU input phase voltage state changes."
				::= { espTraps 15 }
	
espInputphaseCurrentStateChange  	NOTIFICATION-TYPE
					OBJECTS {   espIndex,
								espNamePlateName, 
    	  					    espNamePlateInetAddressType,
	  					    espNamePlateIPAddress,
	  					    espInputPhaseSTATUSCount, 
	  					    espInputPhaseSTATUSCurrentState, 
	  					    espInputPhaseSTATUSCurrent,
	  					    sysContact,
	  					    sysName,
	  					    sysLocation }
					STATUS 	current
					DESCRIPTION 
						"PDU input phase Current state changes."
				::= { espTraps 16 }
	
espCircuitBreakerCurrentStateChange  NOTIFICATION-TYPE
					OBJECTS {   espIndex,
								espNamePlateName, 
    	  					    espNamePlateInetAddressType,
	  					    espNamePlateIPAddress,
	  					    espCircuitBreakerSTATUSIndex, 
	  					    espCircuitBreakerSTATUSLoadState, 
	  					    espCircuitBreakerSTATUSCurrent,
	  					    sysContact,
	  					    sysName,
	  					    sysLocation }
					STATUS 	current
					DESCRIPTION 
						"PDU Circuit Breaker Current state changes."
				::= { espTraps 17 }

espExternalSensorStateChange	NOTIFICATION-TYPE
				OBJECTS {   espIndex,
							espNamePlateName, 
    	  				    espNamePlateInetAddressType,
	  				    espNamePlateIPAddress,
	  				    espExternalSensorSTATUSIndex, 
	  				    espExternalSensorSTATUSName, 
	  				    espExternalSensorNamePlateType, 
					    espExternalSensorSTATUSAisle, 
					    espExternalSensorNamePlateUnits, 
					    espExternalSensorSTATUSState, 
					    espExternalSensorSTATUSValue,
	  				    sysContact,
	  				    sysName,
	  				    sysLocation }
				STATUS 	current
				DESCRIPTION 
					"PDU External Sensor state changes."
				::= { espTraps 18 }	

espConfigurationFileImported  	NOTIFICATION-TYPE
				OBJECTS {   espIndex,
							espNamePlateName, 
    					    userName, 
					    espNamePlateInetAddressType,
					    espNamePlateIPAddress,
					    sysContact,
					    sysName,
					    sysLocation }
				STATUS 	current
				DESCRIPTION 
					"PDU configuration file was imported"
				::= { espTraps 19 }
espNetworkUp  			NOTIFICATION-TYPE
				OBJECTS {   espIndex,
							espNamePlateName, 
    					    userName, 
					    espNamePlateInetAddressType,
					    espNamePlateIPAddress,
					    sysContact,
					    sysName,
					    sysLocation }
				STATUS 	current
				DESCRIPTION 
					"PDU Network is up "
				::= { espTraps 20 }

pod  						OBJECT IDENTIFIER ::= { enlogic 3 }
podNamePlate  					OBJECT IDENTIFIER ::= { pod 1 }
podUnit  					OBJECT IDENTIFIER ::= { pod 2 }
podInputPhase  					OBJECT IDENTIFIER ::= { pod 3 }
podCircuitBreaker  				OBJECT IDENTIFIER ::= { pod 4 }
podOutlet  					OBJECT IDENTIFIER ::= { pod 5 }
podExternalSensor  				OBJECT IDENTIFIER ::= { pod 6 }
podServerPing  					OBJECT IDENTIFIER ::= { pod 7 }
podSmartCabinet  					OBJECT IDENTIFIER ::= { pod 8 }
podTraps						OBJECT IDENTIFIER ::= { pod 9 }

-- Start podNamePlate

podNamePlateTableSize  OBJECT-TYPE
	SYNTAX 	INTEGER(1..256)
	MAX-ACCESS  	read-only
	STATUS 	current
	DESCRIPTION 
		"The total number of PDUs"
	::= { podNamePlate 1 }

-- podNamePlateTable
podNamePlateTable  OBJECT-TYPE
	SYNTAX SEQUENCE OF PodNamePlateEntry
	MAX-ACCESS  	not-accessible
	STATUS 	current
	DESCRIPTION 
		"A table of PDU nameplate data"
	::= { podNamePlate 2 }
	
podNamePlateEntry  OBJECT-TYPE
	SYNTAX 	PodNamePlateEntry
	MAX-ACCESS  	not-accessible
	STATUS 	current
	DESCRIPTION 
		"Nameplate data from the PDU being queried. The numbers of entries equals the value of podNamePlateTableSize."
	INDEX { podNamePlateIndex }
	::= { podNamePlateTable 1 }

PodNamePlateEntry ::= SEQUENCE {
	podNamePlateIndex
		Integer32,
	podNamePlateName
		DisplayString,
	podNamePlateLocation
		DisplayString,
	podNamePlateInetAddressType
		InetAddressType,
	podNamePlateIPAddress
		InetAddress,
	podNamePlateInetNetMask
		InetAddress,
	podNamePlateInetGateway
		InetAddress,
	podNamePlateMACAddress
		MacAddress,
	podNamePlateUTCTimeOffset
		DisplayString,
	podNamePlateModelNumber
		DisplayString,
	podNamePlateSerialNumber
		DisplayString,
	podNamePlateDateofManufacture
		DisplayString,
	podNamePlateFirmwareVersion
		DisplayString,
	podNamePlateFirmwareVersionTimeStamp
		DisplayString,
	podNamePlateType
		INTEGER
	}

podNamePlateIndex  OBJECT-TYPE
	SYNTAX 	INTEGER(1..256)
	MAX-ACCESS  	not-accessible
	STATUS 	current
	DESCRIPTION 
		"The index of the PDU nameplate table entry"
	::= { podNamePlateEntry 1 }
	
podNamePlateName  OBJECT-TYPE
	SYNTAX 	DisplayString
	MAX-ACCESS  	read-only
	STATUS 	current
	DESCRIPTION 
		"A user-defined string identifying the PDU"
	::= { podNamePlateEntry 2 }
	
podNamePlateLocation  OBJECT-TYPE
	SYNTAX 	DisplayString
	MAX-ACCESS  	read-only
	STATUS 	current
	DESCRIPTION 
		"A user-defined string identifying the location of PDU"
	::= { podNamePlateEntry 3 }

podNamePlateInetAddressType  OBJECT-TYPE
	SYNTAX 	InetAddressType
	MAX-ACCESS  	read-only
	STATUS 	current
	DESCRIPTION 
		"The type of address format"
	::= { podNamePlateEntry 4 }

podNamePlateIPAddress  OBJECT-TYPE
	SYNTAX 	InetAddress
	MAX-ACCESS  	read-only
	STATUS 	current
	DESCRIPTION 
		"The current IP address. A value of 0.0.0.0 indicates an error or an unset option"
	::= { podNamePlateEntry 5 }
	
podNamePlateInetNetMask  OBJECT-TYPE
	SYNTAX 	InetAddress
	MAX-ACCESS  	read-only
	STATUS 	current
	DESCRIPTION 
		"The current netmask. A value of 0.0.0.0 indiates an error or an unset option"
	::= { podNamePlateEntry 6 }
	
podNamePlateInetGateway  OBJECT-TYPE
	SYNTAX 	InetAddress
	MAX-ACCESS  	read-only
	STATUS 	current
	DESCRIPTION 
		"The current gateway. A value of 0.0.0.0 indicates an error or an unset option"
	::= { podNamePlateEntry 7 }
	
podNamePlateMACAddress  OBJECT-TYPE
	SYNTAX 	MacAddress
	MAX-ACCESS  	read-only
	STATUS 	current
	DESCRIPTION 
		"The assigned MAC address for the PDU"
	::= { podNamePlateEntry 8 }
	
podNamePlateUTCTimeOffset  OBJECT-TYPE
	SYNTAX 	DisplayString
	MAX-ACCESS  	read-only
	STATUS 	current
	DESCRIPTION 
		"The difference in hours and minutes from Coordinated Universal 
		Time(UTC) for the time used in a particular time zone"
	::= { podNamePlateEntry 9 }
	
podNamePlateModelNumber  OBJECT-TYPE
	SYNTAX 	DisplayString
	MAX-ACCESS  	read-only
	STATUS 	current
	DESCRIPTION 
		"The PDU model number"
	::= { podNamePlateEntry 10 }
	
podNamePlateSerialNumber  OBJECT-TYPE
	SYNTAX 	DisplayString
	MAX-ACCESS  	read-only
	STATUS 	current
	DESCRIPTION 
		"The PDU serial number"
	::= { podNamePlateEntry 11 }
	
podNamePlateDateofManufacture  OBJECT-TYPE
	SYNTAX 	DisplayString
	MAX-ACCESS  	read-only
	STATUS 	current
	DESCRIPTION 
		"The date the PDU was manufactured in mm/dd/yyyy format"
	::= { podNamePlateEntry 12 }

podNamePlateFirmwareVersion  OBJECT-TYPE
	SYNTAX 	DisplayString
	MAX-ACCESS  	read-only
	STATUS 	current
	DESCRIPTION 
		"The PDU firmware version"
	::= { podNamePlateEntry 13 }
	
podNamePlateFirmwareVersionTimeStamp  OBJECT-TYPE
	SYNTAX 	DisplayString
	MAX-ACCESS  	read-only
	STATUS 	current
	DESCRIPTION 
		"Timestamp of when the PDU firmware was last updated"
	::= { podNamePlateEntry 14 }
	
podNamePlateType  OBJECT-TYPE
	SYNTAX 	INTEGER {
		pod (0),
		inlineMeter (1),
		sensorPod (2)
	}
	MAX-ACCESS  	read-only
	STATUS 	current
	DESCRIPTION 
		"The type of Unit, PDU or Inline Meter"
	::= { podNamePlateEntry 15 }
	
	
-- Start podUnit

podUnitTableSize  OBJECT-TYPE
	SYNTAX 	INTEGER(1..256)
	MAX-ACCESS  	read-only
	STATUS 	current
	DESCRIPTION 
		"The number of units."
	::= { podUnit 1 }
	
podUnitConfigTable  OBJECT-TYPE
	SYNTAX SEQUENCE OF PodUnitConfigEntry
	MAX-ACCESS  	not-accessible
	STATUS 	current
	DESCRIPTION 
		"A table of PDU configuration data"
	::= { podUnit 2 }
	
podUnitConfigEntry  OBJECT-TYPE
	SYNTAX 	PodUnitConfigEntry
	MAX-ACCESS  	not-accessible
	STATUS 	current
	DESCRIPTION 
		"Configuration data from the PDU being queried. The number of entries equals the value of podUnitTableSize"
	INDEX { podUnitConfigIndex }
	::= { podUnitConfigTable 1 }

PodUnitConfigEntry ::= SEQUENCE {
	podUnitConfigIndex
		Integer32,
	podUnitConfigName
		DisplayString,
	podUnitConfigLocation
		DisplayString,
	podUnitConfigDisplayOrientation
		INTEGER,
	podUnitConfigColdstartDelay
		Unsigned32,
	podUnitConfigGlobalOutletStateOnStartup
		INTEGER,
	podUnitConfigLowerCriticalThreshold
		Unsigned32,
	podUnitConfigLowerWarningThreshold
		Unsigned32,
	podUnitConfigUpperCriticalThreshold
		Unsigned32,
	podUnitConfigUpperWarningThreshold
		Unsigned32,
	podUnitConfigAlarmResetThreshold
		Unsigned32,
	podUnitConfigAlarmStateChangeDelay
		Unsigned32,
	podUnitConfigEnabledThresholds
		BITS,
	podUnitConfigPeakPowerReset
		INTEGER,
	podUnitConfigEnergyReset
		INTEGER,
	podUnitConfigOutletPeakPowerReset
		INTEGER,
	podUnitConfigOutletEnergyReset
		INTEGER,
	podUnitConfigUsb
		INTEGER,
	podUnitConfigSsh
		INTEGER,
	podUnitConfigResetNetworkManagementCard
		INTEGER,
	podUnitConfigDaisyChainState
		INTEGER
	}

podUnitConfigIndex  OBJECT-TYPE
	SYNTAX 	INTEGER(1..256)
	MAX-ACCESS  	not-accessible
	STATUS 	current
	DESCRIPTION 
		"The index of the PDU Unit Config Entry"
	::= { podUnitConfigEntry 1 }
	
podUnitConfigName  OBJECT-TYPE
	SYNTAX 	DisplayString
	MAX-ACCESS  	read-write
	STATUS 	current
	DESCRIPTION 
		"A user-defined string identifying the PDU"
	::= { podUnitConfigEntry 2 }
	
podUnitConfigLocation  OBJECT-TYPE
	SYNTAX 	DisplayString
	MAX-ACCESS  	read-write
	STATUS 	current
	DESCRIPTION 
		"A user-defined string identifying the location of the PDU"
	::= { podUnitConfigEntry 3 }
	
podUnitConfigDisplayOrientation  OBJECT-TYPE
	SYNTAX 	INTEGER {
		displayNormal (1),
		displayReverse (2)
	}
	MAX-ACCESS  	read-write
	STATUS 	current
	DESCRIPTION 
		"Indicates the intended physical orientation of the oLED display
		displayNormal (1) indicates normal orientation. 
		displayReverse (2) indicates upside down orientation"
	::= { podUnitConfigEntry 4 }
	
podUnitConfigColdstartDelay  OBJECT-TYPE
	SYNTAX 	Unsigned32 (0..3600)
	MAX-ACCESS  	read-write
	STATUS 	current
	DESCRIPTION 
		"The amount of time, specified in seconds, between when power 
		is provided to the PDU and when the PDU start providing basic master
		power to the outlets"
	::= { podUnitConfigEntry 5 }
	
podUnitConfigGlobalOutletStateOnStartup  OBJECT-TYPE
	SYNTAX 	INTEGER {
		off (0),
		on (1),
		lastKnownState (2)
	}
	MAX-ACCESS  	read-write
	STATUS 	current
	DESCRIPTION 
		"The outlet state on device startup; applies to all outlets 
		unless overridden at the outlet level"
	::= { podUnitConfigEntry 6 }
	
podUnitConfigLowerCriticalThreshold  OBJECT-TYPE
	SYNTAX 	Unsigned32
	MAX-ACCESS  	read-write
	STATUS 	current
	DESCRIPTION 
		"User-defined lower critical unit active power alarm threshold measured in Watts"
	::= { podUnitConfigEntry 7 }
	
podUnitConfigLowerWarningThreshold  OBJECT-TYPE
	SYNTAX 	Unsigned32
	MAX-ACCESS  	read-write
	STATUS 	current
	DESCRIPTION 
		"User-defined lower non-critical (warning) unit active power alarm threshold measured in Watts"
	::= { podUnitConfigEntry 8 }
	
podUnitConfigUpperCriticalThreshold  OBJECT-TYPE
	SYNTAX 	Unsigned32
	MAX-ACCESS  	read-write
	STATUS 	current
	DESCRIPTION 
		"User-defined upper critical unit active power alarm threshold measured in Watts"
	::= { podUnitConfigEntry 9 }
	
podUnitConfigUpperWarningThreshold  OBJECT-TYPE
	SYNTAX 	Unsigned32
	MAX-ACCESS  	read-write
	STATUS 	current
	DESCRIPTION 
		"User-defined upper non-critical (warning) unit active power alarm threshold measured in Watts"
	::= { podUnitConfigEntry 10 }
	
podUnitConfigAlarmResetThreshold  OBJECT-TYPE
	SYNTAX 	Unsigned32
	MAX-ACCESS  	read-write
	STATUS 	current
	DESCRIPTION 
		"The hysteresis used for deassertions in Watts"
	::= { podUnitConfigEntry 11 }
	
podUnitConfigAlarmStateChangeDelay  OBJECT-TYPE
	SYNTAX 	Unsigned32
	MAX-ACCESS  	read-write
	STATUS 	current
	DESCRIPTION 
		"The delay measured in samples before a state is asserted. If the value is zero, then the state is asserted as soon as it is detected; if it is non-zero, say n, then the assertion condition must exist for n+1 consecutive samples before the corresponding assertion event is reported."
	::= { podUnitConfigEntry 12 }
	
podUnitConfigEnabledThresholds  OBJECT-TYPE
	SYNTAX 	BITS {
		lowerCritical (0),
		lowerWarning (1),
		upperWarning  (2),
		upperCritical (3)
	}
	MAX-ACCESS  	read-write
	STATUS 	current
	DESCRIPTION 
		"A bit string indicating which alarm thresholds are enabled"
	::= { podUnitConfigEntry 13 }
	
podUnitConfigPeakPowerReset  OBJECT-TYPE
	SYNTAX 	INTEGER {
		noOperation (1),
		reset (2)
	}
	MAX-ACCESS  	read-write
	STATUS 	current
	DESCRIPTION 
		"Setting this OID to reset (2) will cause the existing peak power value 
		to be replaced by the current load power value. Getting this OID will 
		do nothing and return the noOperation(1) value. "
	::= { podUnitConfigEntry 14 }
	
podUnitConfigEnergyReset  OBJECT-TYPE
	SYNTAX 	INTEGER {
		noOperation (1),
		reset (2),
		notSupported (3)
	}
	MAX-ACCESS  	read-write
	STATUS 	current
	DESCRIPTION 
		"Setting this OID to reset (2) will cause the device energy meter value 
		to be reset to zero. Getting this OID in models that support this 
		feature will do nothing and return the noOperation(1) value. Models 
		that do not support this feature will respond to this OID with a 
		value of notSupported (3). Attempts to set this OID in these models will fail. "
	::= { podUnitConfigEntry 15 }

podUnitConfigOutletPeakPowerReset  OBJECT-TYPE
	SYNTAX 	INTEGER {
		noOperation (1),
		reset (2),
		notSupported (3)
	}
	MAX-ACCESS  	read-write
	STATUS 	current
	DESCRIPTION 
		"Setting this OID to reset (2) will cause the outlet peak power meter value 
		to be reset to zero. Getting this OID in models that support this 
		feature will do nothing and return the noOperation(1) value. Models 
		that do not support this feature will respond to this OID with a 
		value of notSupported (3). Attempts to set this OID in these models will fail. "
	::= { podUnitConfigEntry 16 }

podUnitConfigOutletEnergyReset  OBJECT-TYPE
	SYNTAX 	INTEGER {
		noOperation (1),
		reset (2),
		notSupported (3)
	}
	MAX-ACCESS  	read-write
	STATUS 	current
	DESCRIPTION 
		"Setting this OID to reset (2) will cause the outlet energy meter value 
		to be reset to zero. Getting this OID in models that support this 
		feature will do nothing and return the noOperation(1) value. Models 
		that do not support this feature will respond to this OID with a 
		value of notSupported (3). Attempts to set this OID in these models will fail. "
	::= { podUnitConfigEntry 17 }

podUnitConfigUsb  OBJECT-TYPE
	SYNTAX 	INTEGER {
		off (0),
		on (1)
	}
	MAX-ACCESS  	read-write
	STATUS 	current
	DESCRIPTION 
		"Setting this OID to off(0) will disable the USB port.  Setting this OID to on(1) will enable the USB port."
	::= { podUnitConfigEntry 18 }

podUnitConfigSsh  OBJECT-TYPE
	SYNTAX 	INTEGER {
		off (0),
		on (1)
	}
	MAX-ACCESS  	read-write
	STATUS 	current
	DESCRIPTION 
		"Setting this OID to off(0) will disable the SSH connection.  Setting this OID to on(1) will enable the SSH connection."
	::= { podUnitConfigEntry 19 }
	
podUnitConfigResetNetworkManagementCard  OBJECT-TYPE
	SYNTAX 	INTEGER {
		noOperation (0),
		reset (1)
	}
	MAX-ACCESS  	read-write
	STATUS 	current
	DESCRIPTION 
		"Getting this OID will return noOperation(0). Setting this OID to reset(1) will reset NMC."
	::= { podUnitConfigEntry 20 }
	
podUnitConfigDaisyChainState	OBJECT-TYPE
	SYNTAX 	INTEGER {
		daisychain (0)
	}
	MAX-ACCESS  	read-write
	STATUS 	current
	DESCRIPTION 
		"Setting this OID to daisychain(0) will enable daisychain mode."
	::= { podUnitConfigEntry 21 }
	
podUnitPropertiesTable  OBJECT-TYPE
	SYNTAX SEQUENCE OF PodUnitPropertiesEntry
	MAX-ACCESS  	not-accessible
	STATUS 	current
	DESCRIPTION 
		"A table of PDU properties"
	::= { podUnit 3 }
	
podUnitPropertiesEntry  OBJECT-TYPE
	SYNTAX 	PodUnitPropertiesEntry
	MAX-ACCESS  	not-accessible
	STATUS 	current
	DESCRIPTION 
		"A unit properties entry containing objects for a particular unit."
	INDEX { podUnitPropertiesIndex }
	::= { podUnitPropertiesTable 1 }

PodUnitPropertiesEntry ::= SEQUENCE {
	podUnitPropertiesIndex
		Integer32,
	podUnitPropertiesName
		DisplayString,
	podUnitPropertiesOutletCount
		Integer32,
	podUnitPropertiesSwitchedOutletCount
		Integer32,
	podUnitPropertiesMeteredOutletCount
		Integer32,
	podUnitPropertiesInputPhaseCount
		Integer32,
	podUnitPropertiesCircuitBreakerCount
		Integer32,
	podUnitPropertiesMaxExternalSensorCount
		Integer32,
	podUnitPropertiesConnExternalSensorCount
		Integer32,
	podUnitPropertiesRatedVoltage
		DisplayString,
	podUnitPropertiesRatedMaxCurrent
		DisplayString,
	podUnitPropertiesRatedFrequency
		DisplayString,
	podUnitPropertiesRatedPower
		DisplayString,
	podUnitPropertiesOrientation
		INTEGER,
	podUnitPropertiesOutletLayout
		INTEGER,
	podUnitPropertiesDaisyChainMemberType
		INTEGER,
	podUnitPropertiesServerCount
		Integer32
	}

podUnitPropertiesIndex  OBJECT-TYPE
	SYNTAX 	INTEGER(1..256)
	MAX-ACCESS  	not-accessible
	STATUS 	current
	DESCRIPTION 
		"The index of the PDU properties table entry"
	::= { podUnitPropertiesEntry 1 }
	
podUnitPropertiesName  OBJECT-TYPE
	SYNTAX 	DisplayString
	MAX-ACCESS  	read-only
	STATUS 	current
	DESCRIPTION 
		"A user-defined string identifying the PDU"
	::= { podUnitPropertiesEntry 2 }
	
podUnitPropertiesOutletCount  OBJECT-TYPE
	SYNTAX 	INTEGER(1..256)
	MAX-ACCESS  	read-only
	STATUS 	current
	DESCRIPTION 
		"The total number of outlets on the PDU"
	::= { podUnitPropertiesEntry 3 }
	
podUnitPropertiesSwitchedOutletCount  OBJECT-TYPE
	SYNTAX 	INTEGER(1..256)
	MAX-ACCESS  	read-only
	STATUS 	current
	DESCRIPTION 
		"The total number of switched outlets on the PDU"
	::= { podUnitPropertiesEntry 4 }
	
podUnitPropertiesMeteredOutletCount  OBJECT-TYPE
	SYNTAX 	INTEGER(1..256)
	MAX-ACCESS  	read-only
	STATUS 	current
	DESCRIPTION 
		"The total number of metered outlets on the PDU"
	::= { podUnitPropertiesEntry 5 }
	
podUnitPropertiesInputPhaseCount  OBJECT-TYPE
	SYNTAX 	INTEGER(1..256)
	MAX-ACCESS  	read-only
	STATUS 	current
	DESCRIPTION 
		"The total number of phases on the PDU"
	::= { podUnitPropertiesEntry 6 }

podUnitPropertiesCircuitBreakerCount  OBJECT-TYPE
	SYNTAX 	INTEGER(0..255)
	MAX-ACCESS  	read-only
	STATUS 	current
	DESCRIPTION 
		"The total number of circuit breaker on the PDU"
	::= { podUnitPropertiesEntry 7 }
	
podUnitPropertiesMaxExternalSensorCount  OBJECT-TYPE
	SYNTAX 	INTEGER(0..255)
	MAX-ACCESS  	read-only
	STATUS 	current
	DESCRIPTION 
		"The maximum number of external sensors that can be connected to the PDU"
	::= { podUnitPropertiesEntry 8 }
	
podUnitPropertiesConnExternalSensorCount  OBJECT-TYPE
	SYNTAX 	INTEGER(0..255)
	MAX-ACCESS  	read-only
	STATUS 	current
	DESCRIPTION 
		"The current number of external sensors connected to the PDU"
	::= { podUnitPropertiesEntry 9 }
	
podUnitPropertiesRatedVoltage  OBJECT-TYPE
	SYNTAX 	DisplayString
	MAX-ACCESS  	read-only
	STATUS 	current
	DESCRIPTION 
		"The PDU voltage rating in Volts"
	::= { podUnitPropertiesEntry 10 }
	
podUnitPropertiesRatedMaxCurrent  OBJECT-TYPE
	SYNTAX 	DisplayString
	MAX-ACCESS  	read-only
	STATUS 	current
	DESCRIPTION 
		"The PDU current rating in Amps"
	::= { podUnitPropertiesEntry 11 }
	
podUnitPropertiesRatedFrequency  OBJECT-TYPE
	SYNTAX 	DisplayString
	MAX-ACCESS  	read-only
	STATUS 	current
	DESCRIPTION 
		"The PDU frequency rating in Hz"
	::= { podUnitPropertiesEntry 12 }
	
podUnitPropertiesRatedPower  OBJECT-TYPE
	SYNTAX 	DisplayString
	MAX-ACCESS  	read-only
	STATUS 	current
	DESCRIPTION 
		"The PDU VA (VoltAmps) rating."
	::= { podUnitPropertiesEntry 13 }
	
podUnitPropertiesOrientation  OBJECT-TYPE
	SYNTAX 	INTEGER {
		horizontal (1),
		vertical (2)
	}
	MAX-ACCESS  	read-only
	STATUS 	current
	DESCRIPTION 
		"The PDU orientation "
	::= { podUnitPropertiesEntry 14 }
	
podUnitPropertiesOutletLayout  OBJECT-TYPE
	SYNTAX 	INTEGER {
		seqPhaseToNuetral (1),
		seqPhaseToPhase (2),
		seqPhToNeu21PhToPh (3),
		seqPhToPhGrouped (4),
		seqPhToNGrouped (5),
		seqPToN1516PToPGrouped (6),
		seqPhToPh2xGrouped (7),
		seqPhToN2xGrouped (8),
		seqNotApplicable (9)
	}
	MAX-ACCESS  	read-only
	STATUS 	current
	DESCRIPTION 
		"The outlet layout for the PDU. Getting this OID will return outlet layout for the device.
		seqPhaseToNeutral(1) indicates outlet layout as follows:
		1:1-N,2:2-N,3:3-N,4:1-N,5:2-N,...
		seqPhaseToPhase(2) indicates outlet layout as follows:
		1:1-2,2:2-3,3:3-1,4:1-2,5:2-3,...
		seqPhToNeu21PhToPh(3) indicates outlet layout as follows:
		1:1-N,2:2-N...21:3-N,22:1-2,23:2-3,24:3-1,...
		seqPhToPhGrouped(4) indicates outlet layout as follows:
		This unit has 3 outlet groups.  Group 1:1-2, Group 2:2-3, Group 3:3-1.
		seqPhToNGrouped(5) indicates outlet layout as follows:
		This unit has 3 outlet groups.  Group 1:1-N, Group 2:2-N, Group 3:3-N.
		seqPToN1516PToPGrouped(6) indicates outlet layout as follows:
		This unit has 4 outlet groups. Group 1 (Outlets 1-14):1-2,
		Group 2 (Outlets 15-16):1-N, Group 3:2-3, Group 4:3-1.
		seqPhToPh2xGrouped(7) indicates outlet layout as follows:
		This unit has 6 outlet groups.  Group 1:1-2, Group 2:1-2, Group 3:2-3,
		Group 4:2-3, Group 5:3-1, Group 6:3-1.
		seqPhToN2xGrouped(8) indicates outlet layout as follows:
		This unit has 6 outlet groups.  Group 1:1-N, Group 2:1-N, Group 3:2-N,
		Group 4:2-N, Group 5:3-N, Group 6:3-N.
		seqNotApplicable(9):"
	::= { podUnitPropertiesEntry 15 }
	
podUnitPropertiesDaisyChainMemberType  OBJECT-TYPE
	SYNTAX 	INTEGER {
		standalone (1),
		parent (2),
		child (3)
	}
	MAX-ACCESS  	read-only
	STATUS 	current
	DESCRIPTION 
		"The daisy-chain member type"
	::= { podUnitPropertiesEntry 16 }
	
podUnitPropertiesServerCount  OBJECT-TYPE
	SYNTAX 	INTEGER(0..255)
	MAX-ACCESS  	read-only
	STATUS 	current
	DESCRIPTION 
		"The number of servers"
	::= { podUnitPropertiesEntry 17 }
	
podUnitSTATUSTable  OBJECT-TYPE
	SYNTAX SEQUENCE OF PodUnitSTATUSEntry
	MAX-ACCESS  	not-accessible
	STATUS 	current
	DESCRIPTION 
		"A table of PDU STATUS information"
	::= { podUnit 4 }
	
podUnitSTATUSEntry  OBJECT-TYPE
	SYNTAX 	PodUnitSTATUSEntry
	MAX-ACCESS  	not-accessible
	STATUS 	current
	DESCRIPTION 
		"STATUS information from the PDU being queried"
	INDEX { podUnitSTATUSIndex }
	::= { podUnitSTATUSTable 1 }

PodUnitSTATUSEntry ::= SEQUENCE {
	podUnitSTATUSIndex
		Integer32,
	podUnitSTATUSName
		DisplayString,
	podUnitSTATUSLoadState
		INTEGER,
	podUnitSTATUSActivePower
		Integer32,
	podUnitSTATUSApparentPower
		Integer32,
	podUnitSTATUSPeakPower
		Integer32,
	podUnitSTATUSPeakPowerTimestamp
		DisplayString,
	podUnitSTATUSPeakPowerStartTime
		DisplayString,
	podUnitSTATUSEnergy
		Integer32,
	podUnitSTATUSResettableEnergy
		Integer32,
	podUnitSTATUSEnergyStartTime
		DisplayString,
	podUnitSTATUSOutletsEnergyStartTime
		DisplayString
	}

podUnitSTATUSIndex  OBJECT-TYPE
	SYNTAX 	INTEGER(1..256)
	MAX-ACCESS  	not-accessible
	STATUS 	current
	DESCRIPTION 
		"The index of the PDU STATUS table entry"
	::= { podUnitSTATUSEntry 1 }
	
podUnitSTATUSName  OBJECT-TYPE
	SYNTAX 	DisplayString
	MAX-ACCESS  	read-only
	STATUS 	current
	DESCRIPTION 
		"A user-defined string identifying the PDU"
	::= { podUnitSTATUSEntry 2 }
	
podUnitSTATUSLoadState  OBJECT-TYPE
	SYNTAX 	INTEGER {
		upperCritical (1),
		upperWarning (2),
		lowerWarning (3),
		lowerCritical (4),
		normal (5)
	}
	MAX-ACCESS  	read-only
	STATUS 	current
	DESCRIPTION 
		"Returns the present load STATUS of the PDU based on Active Power."
	::= { podUnitSTATUSEntry 3 }
	
podUnitSTATUSActivePower  OBJECT-TYPE
	SYNTAX 	Integer32
	MAX-ACCESS  	read-only
	STATUS 	current
	DESCRIPTION 
		"Returns power consumption, in Watts(W), 
		of the PDU being queried."
	::= { podUnitSTATUSEntry 4 }

podUnitSTATUSApparentPower  OBJECT-TYPE
	SYNTAX 	Integer32
	MAX-ACCESS  	read-only
	STATUS 	current
	DESCRIPTION 
		"Returns power consumption, in Volt-Amps(VA) 
		of the PDU load being queried."
	::= { podUnitSTATUSEntry 5 }
	
podUnitSTATUSPeakPower  OBJECT-TYPE
	SYNTAX 	Integer32
	MAX-ACCESS  	read-only
	STATUS 	current
	DESCRIPTION 
		"Returns peak power consumption, in Watts(W), 
		of the PDU being queried."
	::= { podUnitSTATUSEntry 6 }
	
podUnitSTATUSPeakPowerTimestamp  OBJECT-TYPE
	SYNTAX 	DisplayString
	MAX-ACCESS  	read-only
	STATUS 	current
	DESCRIPTION 
		"Indicates the date and time that peak power consumption occurred"
	::= { podUnitSTATUSEntry 7 }
	
podUnitSTATUSPeakPowerStartTime  OBJECT-TYPE
	SYNTAX 	DisplayString
	MAX-ACCESS  	read-only
	STATUS 	current
	DESCRIPTION 
		"Indicates the date and time of the last device peak power reset"
	::= { podUnitSTATUSEntry 8 }
	
podUnitSTATUSEnergy  OBJECT-TYPE
	SYNTAX 	Integer32
	MAX-ACCESS  	read-only
	STATUS 	current
	DESCRIPTION 
		"Returns total energy consumed, in tenths of Kilowatt-Hours(kWh), of the PDU over its lifetime."		
	::= { podUnitSTATUSEntry 9 }

podUnitSTATUSResettableEnergy  OBJECT-TYPE
	SYNTAX 	Integer32
	MAX-ACCESS  	read-only
	STATUS 	current
	DESCRIPTION 
		"A user resettable energy meter measuring PDU energy consumption 
		in tenths of kilowatt-hours(kWh)."
	::= { podUnitSTATUSEntry 10 }
	
podUnitSTATUSEnergyStartTime  OBJECT-TYPE
	SYNTAX 	DisplayString
	MAX-ACCESS  	read-only
	STATUS 	current
	DESCRIPTION 
		"Indicates the date and time of the last device energy meter reset"
	::= { podUnitSTATUSEntry 11 }
	
podUnitSTATUSOutletsEnergyStartTime  OBJECT-TYPE
	SYNTAX 	DisplayString
	MAX-ACCESS  	read-only
	STATUS 	current
	DESCRIPTION 
		"Indicates the date and time of the last outlets energy meter reset"
	::= { podUnitSTATUSEntry 12 }
	
-- Start podInputPhase
podInputPhaseTableSize  OBJECT-TYPE
	SYNTAX 	INTEGER(1..256)
	MAX-ACCESS  	read-only
	STATUS 	current
	DESCRIPTION 
		"The number of PDU Input Phases "
	::= { podInputPhase 1 }
	
podInputPhaseConfigTable  OBJECT-TYPE
	SYNTAX SEQUENCE OF PodInputPhaseConfigEntry
	MAX-ACCESS  	not-accessible
	STATUS 	current
	DESCRIPTION 
		"A table of PDU Input Phase configuration data"
	::= { podInputPhase 2 }
	
podInputPhaseConfigEntry  OBJECT-TYPE
	SYNTAX 	PodInputPhaseConfigEntry
	MAX-ACCESS  	not-accessible
	STATUS 	current
	DESCRIPTION 
		"An input phase entry containing objects for a particular input phase."
	INDEX { podUnitConfigIndex, podInputPhaseConfigIndex }
	::= { podInputPhaseConfigTable 1 }

PodInputPhaseConfigEntry ::= SEQUENCE {
	podInputPhaseConfigIndex
		Integer32,
	podInputPhaseConfigCount
		Integer32,
	podInputPhaseConfigOverloadRestriction
		INTEGER,
	podInputPhaseConfigCurrentLowerCriticalThreshold
		Unsigned32,
	podInputPhaseConfigCurrentLowerWarningThreshold
		Unsigned32,
	podInputPhaseConfigCurrentUpperCriticalThreshold
		Unsigned32,
	podInputPhaseConfigCurrentUpperWarningThreshold
		Unsigned32,
	podInputPhaseConfigVoltageLowerCriticalThreshold
		Unsigned32,
	podInputPhaseConfigVoltageLowerWarningThreshold
		Unsigned32,
	podInputPhaseConfigVoltageUpperCriticalThreshold
		Unsigned32,
	podInputPhaseConfigVoltageUpperWarningThreshold
		Unsigned32,
	podInputPhaseConfigCurrentAlarmResetThreshold
		Unsigned32,
	podInputPhaseConfigCurrentAlarmStateChangeDelay
		Integer32,
	podInputPhaseConfigCurrentEnabledThresholds
		BITS,
	podInputPhaseConfigVoltageAlarmResetThreshold
		Unsigned32,
	podInputPhaseConfigVoltageAlarmStateChangeDelay
		Integer32,
	podInputPhaseConfigVoltageEnabledThresholds
		BITS
	}

podInputPhaseConfigIndex  OBJECT-TYPE
	SYNTAX 	INTEGER(1..256)
	MAX-ACCESS  	not-accessible
	STATUS 	current
	DESCRIPTION 
		"The index of the PDU Input Phase configuration table entry"
	::= { podInputPhaseConfigEntry 1 }
	
podInputPhaseConfigCount  OBJECT-TYPE
	SYNTAX 	INTEGER(1..256)
	MAX-ACCESS  	read-only
	STATUS 	current
	DESCRIPTION 
		"The total number of Input Phases"
	::= { podInputPhaseConfigEntry 2 }
	
podInputPhaseConfigOverloadRestriction  OBJECT-TYPE
	SYNTAX 	INTEGER {
		alwaysAllowTurnOn (1),
		restrictOnUpperWarning (2),
		restrictOnUpperCritical (3),
		notSupported (4)
	}
	MAX-ACCESS  	read-write
	STATUS 	current
	DESCRIPTION 
		"This OID controls the behavior of a Switched PDU Input Phase when an 
		overload condition is possible and additional outlets are requested 
		to be turned on. Setting this OID to alwaysAllowTurnON (1) will always 
		allow the outlets on the corresponding Input Phase to turn on. Setting 
		this OID to restrictOnUpperWarning (2) will not allow outlets on the 
		corresponding Input Phase to turn on if the 
		podInputPhaseConfigUpperWarningThreshold OID is exceeded. Setting 
		this OID to restrictOnUpperCritical (3) will not allow outlets on 
		the corresponding Input Phase to turn on if the 
		podInputPhaseConfigUpperCriticalThreshold OID is exceeded. Models 
		that do not support this feature will respond to this OID with a 
		value of notSupported (4). Attempts to set this OID in these 
		models will fail. "
	::= { podInputPhaseConfigEntry 3 }
	
podInputPhaseConfigCurrentLowerCriticalThreshold  OBJECT-TYPE
	SYNTAX 	Unsigned32
	MAX-ACCESS  	read-write
	STATUS 	current
	DESCRIPTION 
		"User-defined lower critical input phase current alarm threshold in hundredths of Amps(A)."
	::= { podInputPhaseConfigEntry 4 }
	
podInputPhaseConfigCurrentLowerWarningThreshold  OBJECT-TYPE
	SYNTAX 	Unsigned32
	MAX-ACCESS  	read-write
	STATUS 	current
	DESCRIPTION 
		"User-defined lower non-critical (warning) input phase current alarm threshold in hundredths of Amps(A)."
	::= { podInputPhaseConfigEntry 5 }
	
podInputPhaseConfigCurrentUpperCriticalThreshold  OBJECT-TYPE
	SYNTAX 	Unsigned32
	MAX-ACCESS  	read-write
	STATUS 	current
	DESCRIPTION 
		"User-defined upper critical input phase current alarm threshold in hundredths of Amps(A)."
	::= { podInputPhaseConfigEntry 6 }
	
podInputPhaseConfigCurrentUpperWarningThreshold  OBJECT-TYPE
	SYNTAX 	Unsigned32
	MAX-ACCESS  	read-write
	STATUS 	current
	DESCRIPTION 
		"User-defined upper non-critical (warning) input phase current alarm threshold in hundredths of Amps(A)."
	::= { podInputPhaseConfigEntry 7 }

podInputPhaseConfigVoltageLowerCriticalThreshold  OBJECT-TYPE
	SYNTAX 	Unsigned32
	MAX-ACCESS  	read-write
	STATUS 	current
	DESCRIPTION 
		"User-defined lower critical input phase voltage alarm threshold in Volts(V)."
	::= { podInputPhaseConfigEntry 8 }
	
podInputPhaseConfigVoltageLowerWarningThreshold  OBJECT-TYPE
	SYNTAX 	Unsigned32
	MAX-ACCESS  	read-write
	STATUS 	current
	DESCRIPTION 
		"User-defined lower non-critical (warning) input phase voltage alarm threshold in Volts(V)."
	::= { podInputPhaseConfigEntry 9 }
	
podInputPhaseConfigVoltageUpperCriticalThreshold  OBJECT-TYPE
	SYNTAX 	Unsigned32
	MAX-ACCESS  	read-write
	STATUS 	current
	DESCRIPTION 
		"User-defined upper critical input phase voltage alarm threshold in Volts(V)."
	::= { podInputPhaseConfigEntry 10 }
	
podInputPhaseConfigVoltageUpperWarningThreshold  OBJECT-TYPE
	SYNTAX 	Unsigned32
	MAX-ACCESS  	read-write
	STATUS 	current
	DESCRIPTION 
		"User-defined upper non-critical (warning) input phase voltage alarm threshold in Volts(V)."
	::= { podInputPhaseConfigEntry 11 }
	
podInputPhaseConfigCurrentAlarmResetThreshold  OBJECT-TYPE
	SYNTAX 	Unsigned32
	MAX-ACCESS  	read-write
	STATUS 	current
	DESCRIPTION 
		"The hysteresis used for current alarm deassertions in hundredths of Amps(A)."
	::= { podInputPhaseConfigEntry 12 }
	
podInputPhaseConfigCurrentAlarmStateChangeDelay  OBJECT-TYPE
	SYNTAX 	Integer32
	MAX-ACCESS  	read-write
	STATUS 	current
	DESCRIPTION 
		"The delay measured in samples before a current state is asserted. If the 
		value is zero, then the state is asserted as soon as it is 
		detected; if it is non-zero, say n, then the assertion condition 
		must exist for n+1 consecutive samples before the corresponding 
		assertion event is reported. "
	::= { podInputPhaseConfigEntry 13 }
	
podInputPhaseConfigCurrentEnabledThresholds  OBJECT-TYPE
	SYNTAX 	BITS {
		lowerCritical (0),
		lowerWarning (1),
		upperWarning (2),
		upperCritical (3)
	}
	MAX-ACCESS  	read-write
	STATUS 	current
	DESCRIPTION 
		"A bit string indicating which current alarm thresholds are enabled."
	::= { podInputPhaseConfigEntry 14 }
	
podInputPhaseConfigVoltageAlarmResetThreshold  OBJECT-TYPE
	SYNTAX 	Unsigned32
	MAX-ACCESS  	read-write
	STATUS 	current
	DESCRIPTION 
		"The hysteresis used for voltage alarm deassertions in Volts(V)."
	::= { podInputPhaseConfigEntry 15 }
	
podInputPhaseConfigVoltageAlarmStateChangeDelay  OBJECT-TYPE
	SYNTAX 	Integer32
	MAX-ACCESS  	read-write
	STATUS 	current
	DESCRIPTION 
		"The delay measured in samples before a voltage state is asserted. If the 
		value is zero, then the state is asserted as soon as it is 
		detected; if it is non-zero, say n, then the assertion condition 
		must exist for n+1 consecutive samples before the corresponding 
		assertion event is reported. "
	::= { podInputPhaseConfigEntry 16 }
	
podInputPhaseConfigVoltageEnabledThresholds  OBJECT-TYPE
	SYNTAX 	BITS {
		lowerCritical (0),
		lowerWarning (1),
		upperWarning (2),
		upperCritical (3)
	}
	MAX-ACCESS  	read-write
	STATUS 	current
	DESCRIPTION 
		"A bit string indicating which voltage alarm thresholds are enabled."
	::= { podInputPhaseConfigEntry 17 }
	
podInputPhasePropertiesTable  OBJECT-TYPE
	SYNTAX SEQUENCE OF PodInputPhasePropertiesEntry
	MAX-ACCESS  	not-accessible
	STATUS 	current
	DESCRIPTION 
		"A table of PDU Input Phase properties"
	::= { podInputPhase 3 }
	
podInputPhasePropertiesEntry  OBJECT-TYPE
	SYNTAX 	PodInputPhasePropertiesEntry
	MAX-ACCESS  	not-accessible
	STATUS 	current
	DESCRIPTION 
		"An input phase properties entry containing objects for a particular input phase."
	INDEX { podUnitPropertiesIndex, podInputPhasePropertiesIndex }
	::= { podInputPhasePropertiesTable 1 }

PodInputPhasePropertiesEntry ::= SEQUENCE {
	podInputPhasePropertiesIndex
		Integer32,
	podInputPhasePropertiesCount
		Integer32
	}

podInputPhasePropertiesIndex  OBJECT-TYPE
	SYNTAX 	INTEGER(1..256)
	MAX-ACCESS  	not-accessible
	STATUS 	current
	DESCRIPTION 
		"The index of the PDU Input Phase STATUS entry"
	::= { podInputPhasePropertiesEntry 1 }
	
podInputPhasePropertiesCount  OBJECT-TYPE
	SYNTAX 	INTEGER(1..256)
	MAX-ACCESS  	read-only
	STATUS 	current
	DESCRIPTION 
		"The numeric Input Phase ID"
	::= { podInputPhasePropertiesEntry 2 }
	
podInputPhaseSTATUSTable  OBJECT-TYPE
	SYNTAX SEQUENCE OF PodInputPhaseSTATUSEntry
	MAX-ACCESS  	not-accessible
	STATUS 	current
	DESCRIPTION 
		"A table of PDU Input Phase STATUS data"
	::= { podInputPhase 4 }
	
podInputPhaseSTATUSEntry  OBJECT-TYPE
	SYNTAX 	PodInputPhaseSTATUSEntry
	MAX-ACCESS  	not-accessible
	STATUS 	current
	DESCRIPTION 
		"An input phase STATUS entry containing objects for a particular input phase."
	INDEX { podUnitSTATUSIndex, podInputPhaseSTATUSIndex }
	::= { podInputPhaseSTATUSTable 1 }

PodInputPhaseSTATUSEntry ::= SEQUENCE {
	podInputPhaseSTATUSIndex
		Integer32,
	podInputPhaseSTATUSCount
		Integer32,
	podInputPhaseSTATUSCurrentState
		INTEGER,
	podInputPhaseSTATUSVoltageState
		INTEGER,
	podInputPhaseSTATUSCurrent
		Integer32,
	podInputPhaseSTATUSVoltage
		Integer32,
	podInputPhaseSTATUSActivePower
		Integer32,
	podInputPhaseSTATUSApparentPower
		Integer32,
	podInputPhaseSTATUSPowerFactor
		Integer32
	}

podInputPhaseSTATUSIndex  OBJECT-TYPE
	SYNTAX 	INTEGER(1..256)
	MAX-ACCESS  	not-accessible
	STATUS 	current
	DESCRIPTION 
		"The index of the PDU Input Phase STATUS entry"
	::= { podInputPhaseSTATUSEntry 1 }
	
podInputPhaseSTATUSCount  OBJECT-TYPE
	SYNTAX 	INTEGER(1..256)
	MAX-ACCESS  	read-only
	STATUS 	current
	DESCRIPTION 
		"The numeric Input Phase ID"
	::= { podInputPhaseSTATUSEntry 2 }
	
podInputPhaseSTATUSCurrentState  OBJECT-TYPE
	SYNTAX 	INTEGER {
		upperCritical (1),
		upperWarning (2),
		lowerWarning (3),
		lowerCritical (4),
		normal (5)
	}
	MAX-ACCESS  	read-only
	STATUS 	current
	DESCRIPTION 
		"Indicates the present current STATUS of the PDU Phase in case of Y connection or PDU Line in case of Delta conneciton."
	::= { podInputPhaseSTATUSEntry 3 }
	
podInputPhaseSTATUSVoltageState  OBJECT-TYPE
	SYNTAX 	INTEGER {
		upperCritical (1),
		upperWarning (2),
		lowerWarning (3),
		lowerCritical (4),
		normal (5)
	}
	MAX-ACCESS  	read-only
	STATUS 	current
	DESCRIPTION 
		"Indicates the present voltage STATUS of the PDU Input Phase being queried"
	::= { podInputPhaseSTATUSEntry 4 }
	
podInputPhaseSTATUSCurrent  OBJECT-TYPE
	SYNTAX 	Integer32
	MAX-ACCESS  	read-only
	STATUS 	current
	DESCRIPTION 
		"Returns the current draw, in hundredths of Amps(A), of the load on the 
                PDU Phase/Line being queried. Nodes with 
                podInputPhaseSTATUSIndex from 1 to 3 indicate Y connection  Phase values  or Delta connection Line values,
                and nodes with podInputPhaseSTATUSIndex from 4 to 6 indicate Delta connection Phase values.
		"
	::= { podInputPhaseSTATUSEntry 5 }
	
podInputPhaseSTATUSVoltage  OBJECT-TYPE
	SYNTAX 	Integer32
	MAX-ACCESS  	read-only
	STATUS 	current
	DESCRIPTION 
		"Returns the voltage, in Volts(V), of the PDU Phase/Line being queried.
                 Nodes with podInputPhaseSTATUSIndex from 1  to 3 indicate Y connection Phase values or Delta connection Line values,
                and nodes with podInputPhaseSTATUSIndex from 4 to 6 indicate Delta connection Phase values.
		"
	::= { podInputPhaseSTATUSEntry 6 }
	
podInputPhaseSTATUSActivePower  OBJECT-TYPE
	SYNTAX 	Integer32
	MAX-ACCESS  	read-only
	STATUS 	current
	DESCRIPTION 
		"Returns power consumption, in Watts(W), consumed on the PDU Phase/Line
                being queried. Nodes with podInputPhaseSTATUSIndex from 1 to 3 indicate Y connection
                Phase values or Delta connection Line values, and nodes with 
                podInputPhaseSTATUSIndex from 4 to 6 indicate Delta connection  Phase values.
		"
	::= { podInputPhaseSTATUSEntry 7 }
	
podInputPhaseSTATUSApparentPower  OBJECT-TYPE
	SYNTAX 	Integer32
	MAX-ACCESS  	read-only
	STATUS 	current
	DESCRIPTION 
		"Returns power consumption, in Volt-Amps(VA), of the PDU Phase/Line being queried.
                Nodes with podInputPhaseSTATUSIndex from 1  to 3 indicate Y connection Phase values or Delta connection  Line values,
                and nodes with podInputPhaseSTATUSIndex from 4 to 6 indicate Delta connection  Phase values.
		"
	::= { podInputPhaseSTATUSEntry 8 }
	
podInputPhaseSTATUSPowerFactor  OBJECT-TYPE
	SYNTAX 	Integer32
	MAX-ACCESS  	read-only
	STATUS 	current
	DESCRIPTION 
		"Returns the ratio of active to apparent power of the PDU Phase/Line being queried.
                Nodes with podInputPhaseSTATUSIndex from 1  to 3 indicate Y connection  Phase values or Delta connection Line values,
                and nodes with podInputPhaseSTATUSIndex from 4 to 6 indicate Delta connection  Phase values. 
		"
	::= { podInputPhaseSTATUSEntry 9 }

-- Start podCircuitBreaker
podCircuitBreakerTableSize  OBJECT-TYPE
	SYNTAX 	INTEGER(1..256)
	MAX-ACCESS  	read-only
	STATUS 	current
	DESCRIPTION 
		"The number of PDU Circuit Breakers"
	::= { podCircuitBreaker 1 }
	
podCircuitBreakerConfigTable  OBJECT-TYPE
	SYNTAX SEQUENCE OF PodCircuitBreakerConfigEntry
	MAX-ACCESS  	not-accessible
	STATUS 	current
	DESCRIPTION 
		"A table of PDU Circuit Breaker configuration data"
	::= { podCircuitBreaker 2 }
	
podCircuitBreakerConfigEntry  OBJECT-TYPE
	SYNTAX 	PodCircuitBreakerConfigEntry
	MAX-ACCESS  	not-accessible
	STATUS 	current
	DESCRIPTION 
		"A circuit breaker configuration entry containing objects for a particular circuit breaker."
	INDEX { podUnitConfigIndex, podCircuitBreakerConfigIndex }
	::= { podCircuitBreakerConfigTable 1 }

PodCircuitBreakerConfigEntry ::= SEQUENCE {
	podCircuitBreakerConfigIndex
		Integer32,
	podCircuitBreakerConfigCount
		Integer32,
	podCircuitBreakerName
		DisplayString,
	podCircuitBreakerConfigOverloadRestriction
		INTEGER,
	podCircuitBreakerConfigLowerCriticalThreshold
		Unsigned32,
	podCircuitBreakerConfigLowerWarningThreshold
		Unsigned32,
	podCircuitBreakerConfigUpperCriticalThreshold
		Unsigned32,
	podCircuitBreakerConfigUpperWarningThreshold
		Unsigned32,
	podCircuitBreakerConfigAlarmResetThreshold
		Unsigned32,
	podCircuitBreakerConfigAlarmStateChangeDelay
		Unsigned32,
	podCircuitBreakerConfigEnabledThresholds
		BITS
	}

podCircuitBreakerConfigIndex  OBJECT-TYPE
	SYNTAX 	INTEGER(1..256)
	MAX-ACCESS  	not-accessible
	STATUS 	current
	DESCRIPTION 
		"The index of the PDU Circuit Breaker configuration table entry"
	::= { podCircuitBreakerConfigEntry 1 }
	
podCircuitBreakerConfigCount  OBJECT-TYPE
	SYNTAX 	INTEGER(0..255)
	MAX-ACCESS  	read-only
	STATUS 	current
	DESCRIPTION 
		"The number of circuit breakers on the PDU"
	::= { podCircuitBreakerConfigEntry 2 }
	
podCircuitBreakerName  OBJECT-TYPE
	SYNTAX 	DisplayString
	MAX-ACCESS  	read-only
	STATUS 	current
	DESCRIPTION 
		"The label of the circuit breaker"
	::= { podCircuitBreakerConfigEntry 3 }
	
podCircuitBreakerConfigOverloadRestriction  OBJECT-TYPE
	SYNTAX 	INTEGER {
		alwaysAllowTurnOn (1),
		restrictOnUpperWarning (2),
		restrictOnUpperCritical (3),
		notSupported (4)
	}
	MAX-ACCESS  	read-write
	STATUS 	current
	DESCRIPTION 
		"This OID controls the behavior of a Switched PDU Circuit 
		Breaker when an overload condition is possible and additional 
		outlets are requested to be turned on. Setting this OID to 
		alwaysAllowTurnON (1) will always allow the outlets on the 
		corresponding Circuit Breaker to turn on. Setting this OID 
		to restrictOnUpperWarning (2) will not allow outlets on the 
		corresponding Circuit Breaker to turn on if the 
		podCircuitBreakerConfigUpperWarningThreshold OID is exceeded. 
		Setting this OID to restrictOnUpperCritical (3) will not 
		allow outlets on the corresponding Circuit Breaker to turn 
		on if the podCircuitBreakerConfigUpperCriticalThreshold OID 
		is exceeded. Models that do not support this feature will 
		respond to this OID with a value of notSupported (4). 
		Attempts to set this OID in these models will fail. "
	::= { podCircuitBreakerConfigEntry 4 }

podCircuitBreakerConfigLowerCriticalThreshold  OBJECT-TYPE
	SYNTAX 	Unsigned32
	MAX-ACCESS  	read-write
	STATUS 	current
	DESCRIPTION 
		"User-defined lower critical circuit breaker current alarm threshold in hundredths of Amps(A)."
	::= { podCircuitBreakerConfigEntry 5 }
	
podCircuitBreakerConfigLowerWarningThreshold  OBJECT-TYPE
	SYNTAX 	Unsigned32
	MAX-ACCESS  	read-write
	STATUS 	current
	DESCRIPTION 
		"User-defined lower non-critical (warning) circuit breaker current alarm threshold in hundredths of Amps(A)."
	::= { podCircuitBreakerConfigEntry 6 }
	
podCircuitBreakerConfigUpperCriticalThreshold  OBJECT-TYPE
	SYNTAX 	Unsigned32
	MAX-ACCESS  	read-write
	STATUS 	current
	DESCRIPTION 
		"User-defined upper critical circuit breaker current alarm threshold in hundredths of Amps(A)."
	::= { podCircuitBreakerConfigEntry 7 }
	
podCircuitBreakerConfigUpperWarningThreshold  OBJECT-TYPE
	SYNTAX 	Unsigned32
	MAX-ACCESS  	read-write
	STATUS 	current
	DESCRIPTION 
		"User-defined upper non-critical (warning) circuit breaker current alarm threshold in hundredths of Amps(A)."
	::= { podCircuitBreakerConfigEntry 8 }
	
podCircuitBreakerConfigAlarmResetThreshold  OBJECT-TYPE
	SYNTAX 	Unsigned32
	MAX-ACCESS  	read-write
	STATUS 	current
	DESCRIPTION 
		"The hysteresis used for deassertions in hundredths of Amps(A)."
	::= { podCircuitBreakerConfigEntry 9 }
	
podCircuitBreakerConfigAlarmStateChangeDelay  OBJECT-TYPE
	SYNTAX 	Unsigned32
	MAX-ACCESS  	read-write
	STATUS 	current
	DESCRIPTION 
		"The delay measured in samples before a state is asserted. 
		If the value is zero, then the state is asserted as soon 
		as it is detected; if it is non-zero, say n, then the 
		assertion condition must exist for n+1 consecutive samples 
		before the corresponding assertion event is reported."
	::= { podCircuitBreakerConfigEntry 10 }
	
podCircuitBreakerConfigEnabledThresholds  OBJECT-TYPE
	SYNTAX 	BITS {
		lowerCritical (0),
		lowerWarning (1),
		upperWarning (2),
		upperCritical (3)
	}
	MAX-ACCESS  	read-write
	STATUS 	current
	DESCRIPTION 
		"A bit string indicating which alarm thresholds are enabled."
	::= { podCircuitBreakerConfigEntry 11 }

podCircuitBreakerPropertiesTable  OBJECT-TYPE
	SYNTAX SEQUENCE OF PodCircuitBreakerPropertiesEntry
	MAX-ACCESS  	not-accessible
	STATUS 	current
	DESCRIPTION 
		"A table of PDU circuit breaker properties"
	::= { podCircuitBreaker 3 }

podCircuitBreakerPropertiesEntry  OBJECT-TYPE
	SYNTAX 	PodCircuitBreakerPropertiesEntry
	MAX-ACCESS  	not-accessible
	STATUS 	current
	DESCRIPTION 
		"A circuit breaker properties entry containing objects for a particular circuit breaker."
	INDEX { podUnitPropertiesIndex, podCircuitBreakerPropertiesIndex }
	::= { podCircuitBreakerPropertiesTable 1 }

PodCircuitBreakerPropertiesEntry ::= SEQUENCE {
	podCircuitBreakerPropertiesIndex
		Integer32,
	podCircuitBreakerPropertiesCount
		Integer32,
	podCircuitBreakerPropertiesInputLayout
		INTEGER
	}

podCircuitBreakerPropertiesIndex  OBJECT-TYPE
	SYNTAX 	INTEGER(1..256)
	MAX-ACCESS  	not-accessible
	STATUS 	current
	DESCRIPTION 
		"The index of the PDU Circuit Breaker properties table entry"
	::= { podCircuitBreakerPropertiesEntry 1 }
	
podCircuitBreakerPropertiesCount  OBJECT-TYPE
	SYNTAX 	INTEGER(0..255)
	MAX-ACCESS  	read-only
	STATUS 	current
	DESCRIPTION 
		"The number of Circuit Breakers"
	::= { podCircuitBreakerPropertiesEntry 2 }
	
podCircuitBreakerPropertiesInputLayout  OBJECT-TYPE
	SYNTAX 	INTEGER {
		seqPhase1ToNeutral (1),
		seqPhase2ToNeutral (2),
		seqPhase3ToNeutral (3),
		seqPhase1ToPhase2 (4),
		seqPhase2ToPhase3 (5),
		seqPhase3ToPhase1 (6)
	}
	MAX-ACCESS  	read-only
	STATUS 	current
	DESCRIPTION 
		"This OID describes the outlet phase connections on 
		the referenced bank as follows: 
		seqPhase1ToNeutral(1) indicates that outlets attached 
		to circuit breaker are connected from Phase 1 to Neutral. 
		seqPhase2ToNeutral(2) indicates that outlets attached 
		to circuit breaker are connected from Phase 2 to Neutral. 
		seqPhase3ToNeutral(3) indicates that outlets attached 
		to circuit breaker are connected from Phase 3 to Neutral. 
		seqPhase1ToPhase2(4) indicates that outlets attached 
		to circuit breaker are connected from Phase 1 to Phase2. 
		seqPhase2ToPhase3(5) indicates that outlets attached 
		to circuit breaker are connected from Phase 2 to Phase3.  
		seqPhase3ToPhase1(6) indicates that outlets attached 
		to circuit breaker are connected from Phase 3 to Phase1. "
	::= { podCircuitBreakerPropertiesEntry 3 }
	
podCircuitBreakerSTATUSTable  OBJECT-TYPE
	SYNTAX SEQUENCE OF PodCircuitBreakerSTATUSEntry
	MAX-ACCESS  	not-accessible
	STATUS 	current
	DESCRIPTION 
		"A table of PDU circuit breaker STATUS data"
	::= { podCircuitBreaker 4 }
	
podCircuitBreakerSTATUSEntry  OBJECT-TYPE
	SYNTAX 	PodCircuitBreakerSTATUSEntry
	MAX-ACCESS  	not-accessible
	STATUS 	current
	DESCRIPTION 
		"A circuit breaker STATUS entry containing objects for a particular circuit breaker."
	INDEX { podUnitSTATUSIndex, podCircuitBreakerSTATUSIndex }
	::= { podCircuitBreakerSTATUSTable 1 }

PodCircuitBreakerSTATUSEntry ::= SEQUENCE {
	podCircuitBreakerSTATUSIndex
		Integer32,
	podCircuitBreakerSTATUSCount
		Integer32,
	podCircuitBreakerLabel
		DisplayString,
	podCircuitBreakerSTATUSLoadState
		INTEGER,
	podCircuitBreakerSTATUSCurrent
		Integer32
	}

podCircuitBreakerSTATUSIndex  OBJECT-TYPE
	SYNTAX 	INTEGER(1..256)
	MAX-ACCESS  	not-accessible
	STATUS 	current
	DESCRIPTION 
		"The index of the PDU Circuit Breaker STATUS table entry"
	::= { podCircuitBreakerSTATUSEntry 1 }
	
podCircuitBreakerSTATUSCount  OBJECT-TYPE
	SYNTAX 	INTEGER(0..255)
	MAX-ACCESS  	read-only
	STATUS 	current
	DESCRIPTION 
		"The number of Circuit Breakers"
	::= { podCircuitBreakerSTATUSEntry 2 }
	
podCircuitBreakerLabel  OBJECT-TYPE
	SYNTAX 	DisplayString
	MAX-ACCESS  	read-only
	STATUS 	current
	DESCRIPTION 
		"The label on the PDU identifying the circuit breaker"
	::= { podCircuitBreakerSTATUSEntry 3 }
	
podCircuitBreakerSTATUSLoadState  OBJECT-TYPE
	SYNTAX 	INTEGER {
		upperCritical (1),
		upperWarning (2),
		lowerWarning (3),
		lowerCritical (4),
		normal (5),
		off (6)
	}
	MAX-ACCESS  	read-only
	STATUS 	current
	DESCRIPTION 
		"Indicates the present load STATUS of the PDU Circuit 
		Breaker being queried"
	::= { podCircuitBreakerSTATUSEntry 4 }
	
podCircuitBreakerSTATUSCurrent  OBJECT-TYPE
	SYNTAX 	Integer32
	MAX-ACCESS  	read-only
	STATUS 	current
	DESCRIPTION 
		"Returns the current draw, in hundredths of Amps(A), of the load on 
		the PDU Circuit Breaker being queried."
	::= { podCircuitBreakerSTATUSEntry 5 }
	
-- Start podOutlet
podOutletSwitchedTableSize  OBJECT-TYPE
	SYNTAX 	INTEGER(1..256)
	MAX-ACCESS  	read-only
	STATUS 	current
	DESCRIPTION 
		"The number of PDU Outlets"
	::= { podOutlet 1 }

podOutletSwitchedConfigTable  OBJECT-TYPE
	SYNTAX SEQUENCE OF PodOutletSwitchedConfigEntry
	MAX-ACCESS  	not-accessible
	STATUS 	current
	DESCRIPTION 
		"A table of PDU Switched Outlet configuration data"
	::= { podOutlet 2 }
	
podOutletSwitchedConfigEntry  OBJECT-TYPE
	SYNTAX 	PodOutletSwitchedConfigEntry
	MAX-ACCESS  	not-accessible
	STATUS 	current
	DESCRIPTION 
		"An outlet configuration entry containing objects for a particular outlet."
	INDEX { podUnitConfigIndex, podOutletSwitchedConfigIndex }
	::= { podOutletSwitchedConfigTable 1 }

PodOutletSwitchedConfigEntry ::= SEQUENCE {
	podOutletSwitchedConfigIndex
		Integer32,
	podOutletSwitchedName
		DisplayString,
	podOutletSwitchedStateOnStartup
		INTEGER,
	podOutletSwitchedConfigPowerOnTime
		Integer32,
	podOutletSwitchedConfigPowerOffTime
		Integer32,
	podOutletSwitchedConfigRebootDuration
		Integer32
	}

podOutletSwitchedConfigIndex  OBJECT-TYPE
	SYNTAX 	INTEGER(1..256)
	MAX-ACCESS  	not-accessible
	STATUS 	current
	DESCRIPTION 
		"The index of the PDU Switched Outlet configuration table entry"
	::= { podOutletSwitchedConfigEntry 1 }

podOutletSwitchedName  OBJECT-TYPE
	SYNTAX 	DisplayString
	MAX-ACCESS  	read-write
	STATUS 	current
	DESCRIPTION 
		"The user-defined name for the Switched Outlet"
	::= { podOutletSwitchedConfigEntry 2 }

podOutletSwitchedStateOnStartup  OBJECT-TYPE
	SYNTAX 	INTEGER {
		off (0),
		on (1),
		lastKnownState (2)
		}
	MAX-ACCESS  	read-write
	STATUS 	current
	DESCRIPTION 
		"The outlet state on device startup; overrides 
		the global value podUnitConfigGlobalOutletStateOnStartup."
	::= { podOutletSwitchedConfigEntry 3 }

podOutletSwitchedConfigPowerOnTime  OBJECT-TYPE
	SYNTAX 	Integer32
	MAX-ACCESS  	read-write
	STATUS 	current
	DESCRIPTION 
		"The amount of delay, in seconds, between when power is 
		provided to outlets the outlet and when this outlet 
		starts providing power"
	::= { podOutletSwitchedConfigEntry 4 }

podOutletSwitchedConfigPowerOffTime  OBJECT-TYPE
	SYNTAX 	Integer32
	MAX-ACCESS  	read-write
	STATUS 	current
	DESCRIPTION 
		"The amount of time, in seconds, this outlet will delay 
		powering off"
	::= { podOutletSwitchedConfigEntry 5 }

podOutletSwitchedConfigRebootDuration  OBJECT-TYPE
	SYNTAX 	Integer32
	MAX-ACCESS  	read-write
	STATUS 	current
	DESCRIPTION 
		"The amount of time, in seconds, this outlet will remain 
		in powered off state before returning to power on state 
		during a reboot action."
	::= { podOutletSwitchedConfigEntry 6 }
	
podOutletSwitchedPropertiesTable  OBJECT-TYPE
	SYNTAX SEQUENCE OF PodOutletSwitchedPropertiesEntry
	MAX-ACCESS  	not-accessible
	STATUS 	current
	DESCRIPTION 
		"A table of PDU Switched Outlet properties"
	::= { podOutlet 3 }
	
podOutletSwitchedPropertiesEntry  OBJECT-TYPE
	SYNTAX 	PodOutletSwitchedPropertiesEntry
	MAX-ACCESS  	not-accessible
	STATUS 	current
	DESCRIPTION 
		"An outlet properties entry containing objects for a particular outlet."
	INDEX { podUnitPropertiesIndex, podOutletSwitchedPropertiesIndex }
	::= { podOutletSwitchedPropertiesTable 1 }

PodOutletSwitchedPropertiesEntry ::= SEQUENCE {
	podOutletSwitchedPropertiesIndex
		Integer32,
	podOutletSwitchedPropertiesNumber
		Integer32,
	podOutletSwitchedPropertiesName
		DisplayString,
	podOutletSwitchedPropertiesInputPhaseLayout
		INTEGER,
	podOutletSwitchedPropertiesCircuitBreaker
		Integer32
	}

podOutletSwitchedPropertiesIndex  OBJECT-TYPE
	SYNTAX 	INTEGER(1..256)
	MAX-ACCESS  	not-accessible
	STATUS 	current
	DESCRIPTION 
		"The index of the PDU Switched Outlet properties table entry"
	::= { podOutletSwitchedPropertiesEntry 1 }

podOutletSwitchedPropertiesNumber  OBJECT-TYPE
	SYNTAX 	INTEGER(1..256)
	MAX-ACCESS  	read-only
	STATUS 	current
	DESCRIPTION 
		"The numeric Switched Outlet ID"
	::= { podOutletSwitchedPropertiesEntry 2 }

podOutletSwitchedPropertiesName  OBJECT-TYPE
	SYNTAX 	DisplayString
	MAX-ACCESS  	read-only
	STATUS 	current
	DESCRIPTION 
		"The user-defined switched outlet ID string"
	::= { podOutletSwitchedPropertiesEntry 3 }
	
podOutletSwitchedPropertiesInputPhaseLayout  OBJECT-TYPE
	SYNTAX 	INTEGER {
		seqPhase1ToNeutral (1),
		seqPhase2ToNeutral (2),
		seqPhase3ToNeutral (3),
		seqPhase1ToPhase2 (4),
		seqPhase2ToPhase3 (5),
		seqPhase3ToPhase1 (6)
	}
	MAX-ACCESS  	read-only
	STATUS 	current
	DESCRIPTION 
		"This OID describes the outlet phase connections 
		on the referenced bank as follows: 
		seqPhase1ToNeutral(1) indicates that outlets 
		attached to Switched Outlet are connected from Phase 1 to Neutral. 
		seqPhase2ToNeutral(2) indicates that outlets 
		attached to Switched Outlet are connected from Phase 2 to Neutral. 
		seqPhase3ToNeutral(3) indicates that outlets 
		attached to Switched Outlet are connected from Phase 3 to Neutral. 
		seqPhase1ToPhase2(4) indicates that outlets 
		attached to Switched Outlet are connected from Phase 1 to Phase2. 
		seqPhase2ToPhase3(5) indicates that outlets 
		attached to Switched Outlet are connected from Phase 2 to Phase3.  
		seqPhase3ToPhase1(6) indicates that outlets 
		attached to Switched Outlet are connected from Phase 3 to Phase1. "
	::= { podOutletSwitchedPropertiesEntry 4 }

podOutletSwitchedPropertiesCircuitBreaker  OBJECT-TYPE
	SYNTAX 	INTEGER(1..256)
	MAX-ACCESS  	read-only
	STATUS 	current
	DESCRIPTION 
		"The numeric Circuit Breaker ID"
	::= { podOutletSwitchedPropertiesEntry 5 }

podOutletSwitchedSTATUSTable  OBJECT-TYPE
	SYNTAX SEQUENCE OF PodOutletSwitchedSTATUSEntry
	MAX-ACCESS  	not-accessible
	STATUS 	current
	DESCRIPTION 
		"A table of PDU Switched Outlet STATUS data"
	::= { podOutlet 4 }

podOutletSwitchedSTATUSEntry  OBJECT-TYPE
	SYNTAX 	PodOutletSwitchedSTATUSEntry
	MAX-ACCESS  	not-accessible
	STATUS 	current
	DESCRIPTION 
		"STATUS data from the PDU Switched Outlet being queried"
	INDEX { podUnitSTATUSIndex, podOutletSwitchedSTATUSIndex }
	::= { podOutletSwitchedSTATUSTable 1 }

PodOutletSwitchedSTATUSEntry ::= SEQUENCE {
	podOutletSwitchedSTATUSIndex
		Integer32,
	podOutletSwitchedSTATUSNumber
		Integer32,
	podOutletSwitchedSTATUSName
		DisplayString,
	podOutletSwitchedSTATUSState
		INTEGER
	}

podOutletSwitchedSTATUSIndex  OBJECT-TYPE
	SYNTAX 	INTEGER(1..256)
	MAX-ACCESS  	not-accessible
	STATUS 	current
	DESCRIPTION 
		"The index of the PDU Switched Outlet STATUS table entry"
	::= { podOutletSwitchedSTATUSEntry 1 }

podOutletSwitchedSTATUSNumber  OBJECT-TYPE
	SYNTAX 	INTEGER(1..256)
	MAX-ACCESS  	read-only
	STATUS 	current
	DESCRIPTION 
		"The numeric Switched Outlet ID"
	::= { podOutletSwitchedSTATUSEntry 2 }

podOutletSwitchedSTATUSName  OBJECT-TYPE
	SYNTAX 	DisplayString
	MAX-ACCESS  	read-only
	STATUS 	current
	DESCRIPTION 
		"The user-defined switched outlet ID string"
	::= { podOutletSwitchedSTATUSEntry 3 }

podOutletSwitchedSTATUSState  OBJECT-TYPE
	SYNTAX 	INTEGER {
		off (0),
		on (1)
	}
	MAX-ACCESS  	read-only
	STATUS 	current
	DESCRIPTION 
		"Indicates the present switch state of the 
		PDU switched outlet being queried"
	::= { podOutletSwitchedSTATUSEntry 4 }
	
podOutletSwitchedControlTable  OBJECT-TYPE
	SYNTAX SEQUENCE OF PodOutletSwitchedControlEntry
	MAX-ACCESS  	not-accessible
	STATUS 	current
	DESCRIPTION 
		"A table of PDU Switched Outlet STATUS data"
	::= { podOutlet 5 }
	
podOutletSwitchedControlEntry  OBJECT-TYPE
	SYNTAX 	PodOutletSwitchedControlEntry
	MAX-ACCESS  	not-accessible
	STATUS 	current
	DESCRIPTION 
		"STATUS data from the PDU Switched Outlet 
		being queried"
	INDEX { podUnitConfigIndex, podOutletSwitchedControlIndex }
	::= { podOutletSwitchedControlTable 1 }

PodOutletSwitchedControlEntry ::= SEQUENCE {
	podOutletSwitchedControlIndex
		Integer32,
	podOutletSwitchedControlNumber
		Integer32,
	podOutletSwitchedControlName
		DisplayString,
	podOutletSwitchedControlCommand
		INTEGER
	}

podOutletSwitchedControlIndex  OBJECT-TYPE
	SYNTAX 	INTEGER(1..256)
	MAX-ACCESS  	not-accessible
	STATUS 	current
	DESCRIPTION 
		"The index to the PDU switched outlet 
		control data table entry"
	::= { podOutletSwitchedControlEntry 1 }
	
podOutletSwitchedControlNumber  OBJECT-TYPE
	SYNTAX 	INTEGER(1..256)
	MAX-ACCESS  	read-only
	STATUS 	current
	DESCRIPTION 
		"The numeric Switched Outlet ID"
	::= { podOutletSwitchedControlEntry 2 }
	
podOutletSwitchedControlName  OBJECT-TYPE
	SYNTAX 	DisplayString
	MAX-ACCESS  	read-only
	STATUS 	current
	DESCRIPTION 
		"The user-defined switched outlet ID string"
	::= { podOutletSwitchedControlEntry 3 }

podOutletSwitchedControlCommand  OBJECT-TYPE
	SYNTAX 	INTEGER {
		immediateOff (1),
		immediateOn (2),
		delayedOff (3),
		delayedOn (4),
		immediateReboot (5),
		delayedReboot (6),
		outletUnknown (7)
		}
	MAX-ACCESS  	read-write
	STATUS 	current
	DESCRIPTION 
		"Getting this variable will return the outlet state.
		If the outlet is on, the immediateOn (2) 
		value will be returned. If the outlet is off, 
		the immediateOff (1) value will be returned. 
		If the state of the outlet cannot be determined, the 
		outletUnknown (7) value will be returned. If the 
		outletUnknown condition should occur, all devices 
		powered by the PDU should be shut down. The PDU's 
		power should then be cycled to clear this condition. 
		Setting this variable to immediateOn (2) will immediately 
		turn the outlet on. Setting this variable to 
		immediateOff (1) will immediately turn the outlet off. 
		Setting this variable to immediateReboot (5) 
		will cause the Switched PDU to perform an immediateOff 
		command, wait the podOutletSwitchedConfigRebootDuration 
		OID time, and then perform an immediateOn command.
		Setting this variable to delayedOn (4) will turn the 
		outlet on after the podOutletSwitchedConfigPowerOnTime 
		OID time has elapsed. Setting this variable to 
		delayedOff (3) will turn the outlet off after the 
		podOutletSwitchedConfigPowerOffTime OID time has elapsed. 
		Setting this variable to delayedReboot  (6) will cause 
		the Switched PDU to perform a delayedOff command, wait 
		the podOutletSwitchedConfigRebootDuration OID time, and 
		then perform a delayedOn command."
	::= { podOutletSwitchedControlEntry 4 }

podOutletMeteredTableSize  OBJECT-TYPE
	SYNTAX 	INTEGER(1..256)
	MAX-ACCESS  	read-only
	STATUS 	current
	DESCRIPTION 
		"The number of PDU Outlets"
	::= { podOutlet 6 }

podOutletMeteredConfigTable  OBJECT-TYPE
	SYNTAX SEQUENCE OF PodOutletMeteredConfigEntry
	MAX-ACCESS  	not-accessible
	STATUS 	current
	DESCRIPTION 
		"A table of PDU Metered Outlet configuration data"
	::= { podOutlet 7 }

podOutletMeteredConfigEntry  OBJECT-TYPE
	SYNTAX 	PodOutletMeteredConfigEntry
	MAX-ACCESS  	not-accessible
	STATUS 	current
	DESCRIPTION 
		"An outlet configuration entry containing objects for a particular outlet."
	INDEX { podUnitConfigIndex, podOutletMeteredConfigIndex }
	::= { podOutletMeteredConfigTable 1 }

PodOutletMeteredConfigEntry ::= SEQUENCE {
	podOutletMeteredConfigIndex
		Integer32,
	podOutletMeteredName
		DisplayString,
	podOutletMeteredConfigLowerCriticalThreshold
		Unsigned32,
	podOutletMeteredConfigLowerWarningThreshold
		Unsigned32,
	podOutletMeteredConfigUpperCriticalThreshold
		Unsigned32,
	podOutletMeteredConfigUpperWarningThreshold
		Unsigned32,
	podOutletMeteredConfigAlarmResetThreshold
		Unsigned32,
	podOutletMeteredConfigAlarmStateChangeDelay
		Unsigned32,
	podOutletMeteredConfigEnabledThresholds
		BITS
	}

podOutletMeteredConfigIndex  OBJECT-TYPE
	SYNTAX 	INTEGER(1..256)
	MAX-ACCESS  	not-accessible
	STATUS 	current
	DESCRIPTION 
		"The index of the PDU Metered Outlet 
		configuration table entry"
	::= { podOutletMeteredConfigEntry 1 }

podOutletMeteredName  OBJECT-TYPE
	SYNTAX 	DisplayString
	MAX-ACCESS  	read-write
	STATUS 	current
	DESCRIPTION 
		"The user-defined name for the Metered Outlet"
	::= { podOutletMeteredConfigEntry 2 }

podOutletMeteredConfigLowerCriticalThreshold  OBJECT-TYPE
	SYNTAX 	Unsigned32
	MAX-ACCESS  	read-write
	STATUS 	current
	DESCRIPTION 
		"User-defined lower critical outlet active power alarm threshold in Watts(W)."
	::= { podOutletMeteredConfigEntry 3 }

podOutletMeteredConfigLowerWarningThreshold  OBJECT-TYPE
	SYNTAX 	Unsigned32
	MAX-ACCESS  	read-write
	STATUS 	current
	DESCRIPTION 
		"User-defined lower non-critical (warning) outlet active power alarm threshold in Watts(W)."
	::= { podOutletMeteredConfigEntry 4 }

podOutletMeteredConfigUpperCriticalThreshold  OBJECT-TYPE
	SYNTAX 	Unsigned32
	MAX-ACCESS  	read-write
	STATUS 	current
	DESCRIPTION 
		"User-defined upper critical outlet active power alarm threshold in Watts(W)."
	::= { podOutletMeteredConfigEntry 5 }

podOutletMeteredConfigUpperWarningThreshold  OBJECT-TYPE
	SYNTAX 	Unsigned32
	MAX-ACCESS  	read-write
	STATUS 	current
	DESCRIPTION 
		"User-defined upper non-critical (warning) outlet active power alarm threshold in Watts(W)."
	::= { podOutletMeteredConfigEntry 6 }

podOutletMeteredConfigAlarmResetThreshold  OBJECT-TYPE
	SYNTAX 	Unsigned32
	MAX-ACCESS  	read-write
	STATUS 	current
	DESCRIPTION 
		"The hysteresis used for deassertions in Watts(W)."
	::= { podOutletMeteredConfigEntry 7 }

podOutletMeteredConfigAlarmStateChangeDelay  OBJECT-TYPE
	SYNTAX 	Unsigned32
	MAX-ACCESS  	read-write
	STATUS 	current
	DESCRIPTION 
		"The delay measured in samples before a state 
		is asserted. If the value is zero, then the state 
		is asserted as soon as it is detected; if it is 
		non-zero, say n, then the assertion condition must 
		exist for n+1 consecutive samples before the 
		corresponding assertion event is reported."
	::= { podOutletMeteredConfigEntry 8 }

podOutletMeteredConfigEnabledThresholds  OBJECT-TYPE
	SYNTAX 	BITS {
		lowerCritical (0),
		lowerWarning (1),
		upperWarning (2),
		upperCritical (3)
	}
	MAX-ACCESS  	read-write
	STATUS 	current
	DESCRIPTION 
		"A bit string indicating which alarm 
		thresholds are enabled."
	::= { podOutletMeteredConfigEntry 9 }

podOutletMeteredPropertiesTable  OBJECT-TYPE
	SYNTAX SEQUENCE OF PodOutletMeteredPropertiesEntry
	MAX-ACCESS  	not-accessible
	STATUS 	current
	DESCRIPTION 
		"A table of PDU Metered Outlet properties"
	::= { podOutlet 8 }

podOutletMeteredPropertiesEntry  OBJECT-TYPE
	SYNTAX 	PodOutletMeteredPropertiesEntry
	MAX-ACCESS  	not-accessible
	STATUS 	current
	DESCRIPTION 
		"Configuration data from the PDU Metered 
		Outlet being queried"
	INDEX { podUnitPropertiesIndex, podOutletMeteredPropertiesIndex }
	::= { podOutletMeteredPropertiesTable 1 }

PodOutletMeteredPropertiesEntry ::= SEQUENCE {
	podOutletMeteredPropertiesIndex
		Integer32,
	podOutletMeteredPropertiesNumber
		Integer32,
	podOutletMeteredPropertiesName
		DisplayString,
	podOutletMeteredPropertiesInputPhaseLayout
		INTEGER,
	podOutletMeteredPropertiesCircuitBreaker
		Integer32,
	podOutletMeteredPropertiesPowerRating
		Integer32
	}

podOutletMeteredPropertiesIndex  OBJECT-TYPE
	SYNTAX 	INTEGER(1..256)
	MAX-ACCESS  	not-accessible
	STATUS 	current
	DESCRIPTION 
		"The index of the PDU Metered Outlet 
		properties table entry"
	::= { podOutletMeteredPropertiesEntry 1 }

podOutletMeteredPropertiesNumber  OBJECT-TYPE
	SYNTAX 	INTEGER(1..256)
	MAX-ACCESS  	read-only
	STATUS 	current
	DESCRIPTION 
		"The numeric Metered Outlet ID"
	::= { podOutletMeteredPropertiesEntry 2 }

podOutletMeteredPropertiesName  OBJECT-TYPE
	SYNTAX 	DisplayString
	MAX-ACCESS  	read-only
	STATUS 	current
	DESCRIPTION 
		"The user-defined Metered outlet ID string"
	::= { podOutletMeteredPropertiesEntry 3 }

podOutletMeteredPropertiesInputPhaseLayout  OBJECT-TYPE
	SYNTAX 	INTEGER {
		seqPhase1ToNeutral (1),
		seqPhase2ToNeutral (2),
		seqPhase3ToNeutral (3),
		seqPhase1ToPhase2 (4),
		seqPhase2ToPhase3 (5),
		seqPhase3ToPhase1 (6)
	}
	MAX-ACCESS  	read-only
	STATUS 	current
	DESCRIPTION 
		"This OID describes the outlet phase connections 
		on the referenced bank as follows: 
		seqPhase1ToNeutral(1) indicates that outlets attached 
		to Metered Outlet are connected from Phase 1 to Neutral. 
		seqPhase2ToNeutral(2) indicates that outlets attached 
		to Metered Outlet are connected from Phase 2 to Neutral. 
		seqPhase3ToNeutral(3) indicates that outlets attached 
		to Metered Outlet are connected from Phase 3 to Neutral. 
		seqPhase1ToPhase2(4) indicates that outlets attached 
		to Metered Outlet are connected from Phase 1 to Phase2. 
		seqPhase2ToPhase3(5) indicates that outlets attached 
		to Metered Outlet are connected from Phase 2 to Phase3.  
		seqPhase3ToPhase1(6) indicates that outlets attached 
		to Metered Outlet are connected from Phase 3 to Phase1. "
	::= { podOutletMeteredPropertiesEntry 4 }

podOutletMeteredPropertiesCircuitBreaker  OBJECT-TYPE
	SYNTAX 	INTEGER(1..256)
	MAX-ACCESS  	read-only
	STATUS 	current
	DESCRIPTION 
		"The numeric Circuit Breaker ID"
	::= { podOutletMeteredPropertiesEntry 5 }

podOutletMeteredPropertiesPowerRating  OBJECT-TYPE
	SYNTAX 	Integer32
	MAX-ACCESS  	read-only
	STATUS 	current
	DESCRIPTION 
		"Maximum power rating of the PDU metered outlet"
	::= { podOutletMeteredPropertiesEntry 6 }
	
podOutletMeteredSTATUSTable  OBJECT-TYPE
	SYNTAX SEQUENCE OF PodOutletMeteredSTATUSEntry
	MAX-ACCESS  	not-accessible
	STATUS 	current
	DESCRIPTION 
		"A table of PDU Metered Outlet STATUS data"
	::= { podOutlet 9 }
	
podOutletMeteredSTATUSEntry  OBJECT-TYPE
	SYNTAX 	PodOutletMeteredSTATUSEntry
	MAX-ACCESS  	not-accessible
	STATUS 	current
	DESCRIPTION 
		"STATUS data from the PDU Metered Outlet being queried"
	INDEX { podUnitSTATUSIndex, podOutletMeteredSTATUSIndex }
	::= { podOutletMeteredSTATUSTable 1 }

PodOutletMeteredSTATUSEntry ::= SEQUENCE {
	podOutletMeteredSTATUSIndex
		Integer32,
	podOutletMeteredSTATUSNumber
		Integer32,
	podOutletMeteredSTATUSName
		DisplayString,
	podOutletMeteredSTATUSLoadState
		INTEGER,
	podOutletMeteredSTATUSCurrent
		Integer32,
	podOutletMeteredSTATUSActivePower
		Integer32,
	podOutletMeteredSTATUSPowerFactor
		Integer32,
	podOutletMeteredSTATUSPeakPower
		Integer32,
	podOutletMeteredSTATUSPeakPowerTimeStamp
		DisplayString,
	podOutletMeteredSTATUSPeakPowerStartTime
		DisplayString,
	podOutletMeteredSTATUSResettableEnergy
		Integer32
	}

podOutletMeteredSTATUSIndex  OBJECT-TYPE
	SYNTAX 	INTEGER(1..256)
	MAX-ACCESS  	not-accessible
	STATUS 	current
	DESCRIPTION 
		"The index of the PDU Metered Outlet STATUS table entry"
	::= { podOutletMeteredSTATUSEntry 1 }

podOutletMeteredSTATUSNumber  OBJECT-TYPE
	SYNTAX 	INTEGER(1..256)
	MAX-ACCESS  	read-only
	STATUS 	current
	DESCRIPTION 
		"The numeric Metered Outlet ID"
	::= { podOutletMeteredSTATUSEntry 2 }

podOutletMeteredSTATUSName  OBJECT-TYPE
	SYNTAX 	DisplayString
	MAX-ACCESS  	read-only
	STATUS 	current
	DESCRIPTION 
		"The user-defined Metered outlet ID string"
	::= { podOutletMeteredSTATUSEntry 3 }
	
podOutletMeteredSTATUSLoadState  OBJECT-TYPE
	SYNTAX 	INTEGER {
		upperCritical (1),
		upperWarning (2),
		lowerWarning (3),
		lowerCritical (4),
		normal (5)
	}
	MAX-ACCESS  	read-only
	STATUS 	current
	DESCRIPTION 
		"Returns the present load STATUS of the PDU metered outlet being queried."
	::= { podOutletMeteredSTATUSEntry 4 }

podOutletMeteredSTATUSCurrent  OBJECT-TYPE
	SYNTAX 	Integer32
	MAX-ACCESS  	read-only
	STATUS 	current
	DESCRIPTION 
		"Returns the current draw, in hundredths of Amps(A), of the load on the PDU 
		outlet being queried."
	::= { podOutletMeteredSTATUSEntry 5 }

podOutletMeteredSTATUSActivePower  OBJECT-TYPE
	SYNTAX 	Integer32
	MAX-ACCESS  	read-only
	STATUS 	current
	DESCRIPTION 
		"Returns the power draw, in Watts(W), of the load 
		on the PDU outlet being queried."
	::= { podOutletMeteredSTATUSEntry 6 }
	
podOutletMeteredSTATUSPowerFactor  OBJECT-TYPE
	SYNTAX 	Integer32
	MAX-ACCESS  	read-only
	STATUS 	current
	DESCRIPTION 
		"Returns the ratio of active to apparent power 
		of the PDU Outlet being queried"
	::= { podOutletMeteredSTATUSEntry 7 }

podOutletMeteredSTATUSPeakPower  OBJECT-TYPE
	SYNTAX 	Integer32
	MAX-ACCESS  	read-only
	STATUS 	current
	DESCRIPTION 
		"Returns peak power consumption, in Watts(W), 
		of the Rack PDU outlet being queried."
	::= { podOutletMeteredSTATUSEntry 8 }

podOutletMeteredSTATUSPeakPowerTimeStamp  OBJECT-TYPE
	SYNTAX 	DisplayString
	MAX-ACCESS  	read-only
	STATUS 	current
	DESCRIPTION 
		"Indicates the date and time that this metered 
		outlet's peak power consumption occurred"
	::= { podOutletMeteredSTATUSEntry 9 }

podOutletMeteredSTATUSPeakPowerStartTime  OBJECT-TYPE
	SYNTAX 	DisplayString
	MAX-ACCESS  	read-only
	STATUS 	current
	DESCRIPTION 
		"Indicates the start date and time that this metered 
		outlet began recording peak power observations"
	::= { podOutletMeteredSTATUSEntry 10 }

podOutletMeteredSTATUSResettableEnergy  OBJECT-TYPE
	SYNTAX 	Integer32
	MAX-ACCESS  	read-only
	STATUS 	current
	DESCRIPTION 
		"A user resettable energy meter measuring outlet load energy 
		consumption in tenths of Kilowatt-Hours(kWh)."
	::= { podOutletMeteredSTATUSEntry 11 }

-- Start podExternalSensor
podExternalSensorTableSize  OBJECT-TYPE
	SYNTAX 	INTEGER(1..256)
	MAX-ACCESS  	read-only
	STATUS 	current
	DESCRIPTION 
		"The total number of External Sensors"
	::= { podExternalSensor 1 }

podExternalSensorNamePlateTable  OBJECT-TYPE
	SYNTAX SEQUENCE OF PodExternalSensorNamePlateEntry
	MAX-ACCESS  	not-accessible
	STATUS 	current
	DESCRIPTION 
		"A table of PDU ExternalSensorNamePlate data"
	::= { podExternalSensor 2 }

podExternalSensorNamePlateEntry  OBJECT-TYPE
	SYNTAX 	PodExternalSensorNamePlateEntry
	MAX-ACCESS  	not-accessible
	STATUS 	current
	DESCRIPTION 
		"External Sensor Name Plate data from the external 
		sensor being queried. The number of entries equals 
		the value of podExternalSensorNamePlateTableSize."
	INDEX { podNamePlateIndex, podExternalSensorNamePlateIndex }
	::= { podExternalSensorNamePlateTable 1 }

PodExternalSensorNamePlateEntry ::= SEQUENCE {
	podExternalSensorNamePlateIndex
		Integer32,
	podExternalSensorNamePlateName
		DisplayString,
	podExternalSensorNamePlateDescription
		DisplayString,
	podExternalSensorNamePlateLocation
		DisplayString,
	podExternalSensorNamePlateSerialNumber
		DisplayString,
	podExternalSensorNamePlateType
		INTEGER,
	podExternalSensorNamePlateUnits
		INTEGER,
	podExternalSensorNamePlateIdentifier
		Integer32
	}

podExternalSensorNamePlateIndex  OBJECT-TYPE
	SYNTAX 	INTEGER(0..255)
	MAX-ACCESS  	not-accessible
	STATUS 	current
	DESCRIPTION 
		"The index of the PDU External Sensor STATUS table entry"
	::= { podExternalSensorNamePlateEntry 1 }

podExternalSensorNamePlateName  OBJECT-TYPE
	SYNTAX 	DisplayString
	MAX-ACCESS  	read-write
	STATUS 	current
	DESCRIPTION 
		"A user-defined string identifying the external sensor"
	::= { podExternalSensorNamePlateEntry 2 }

podExternalSensorNamePlateDescription  OBJECT-TYPE
	SYNTAX 	DisplayString
	MAX-ACCESS  	read-write
	STATUS 	current
	DESCRIPTION 
		"A user-defined description of the external sensor"
	::= { podExternalSensorNamePlateEntry 3 }

podExternalSensorNamePlateLocation  OBJECT-TYPE
	SYNTAX 	DisplayString
	MAX-ACCESS  	read-write
	STATUS 	current
	DESCRIPTION 
		"A user-defined string identifying the location of the PDU"
	::= { podExternalSensorNamePlateEntry 4 }

podExternalSensorNamePlateSerialNumber  OBJECT-TYPE
	SYNTAX 	DisplayString
	MAX-ACCESS  	read-only
	STATUS 	current
	DESCRIPTION 
		"The serial number of the external sensor being queried"
	::= { podExternalSensorNamePlateEntry 5 }

podExternalSensorNamePlateType  OBJECT-TYPE
	SYNTAX 	INTEGER {
		temperature (1),
		humidity (2),
		doorSwitch (3),
		dryContact (4),
		spotFluid (5),
		ropeFluid (6),
		smoke (7),
		beacon (8),
		airVelocity (9),
		modbusAdapter (17),
		hidAdapter (18)
	}
	MAX-ACCESS  	read-only
	STATUS 	current
	DESCRIPTION 
		"The type of external sensor."
	::= { podExternalSensorNamePlateEntry 6 }

podExternalSensorNamePlateUnits  OBJECT-TYPE
	SYNTAX 	INTEGER {
		logic (0),
		degreeC (1),
		degreeF (2),
		percent (3),
		mps (4)
	}
	MAX-ACCESS  	read-only
	STATUS 	current
	DESCRIPTION 
		"The base units the external sensor is measured in. 
		This parameter does not apply to onOff, trip, vibration,
		 waterDetection, smokeDetection sensors. "
	::= { podExternalSensorNamePlateEntry 7 }

podExternalSensorNamePlateIdentifier  OBJECT-TYPE
	SYNTAX 	Integer32
	MAX-ACCESS  	read-only
	STATUS 	current
	DESCRIPTION 
		"Unique identifier of the external sensor."
	::= { podExternalSensorNamePlateEntry 8 }

podExternalSensorConfigTable  OBJECT-TYPE
	SYNTAX SEQUENCE OF PodExternalSensorConfigEntry
	MAX-ACCESS  	not-accessible
	STATUS 	current
	DESCRIPTION 
		"A table of PDU External Sensor configuration data"
	::= { podExternalSensor 3 }

podExternalSensorConfigEntry  OBJECT-TYPE
	SYNTAX 	PodExternalSensorConfigEntry
	MAX-ACCESS  	not-accessible
	STATUS 	current
	DESCRIPTION 
		"Configuration data from the PDU External 
		Sensor being queried"
	INDEX { podUnitConfigIndex, podExternalSensorConfigIndex }
	::= { podExternalSensorConfigTable 1 }

PodExternalSensorConfigEntry ::= SEQUENCE {
	podExternalSensorConfigIndex
		Integer32,
	podExternalSensorConfigLowerCriticalThreshold
		Unsigned32,
	podExternalSensorConfigLowerWarningThreshold
		Unsigned32,
	podExternalSensorConfigUpperCriticalThreshold
		Unsigned32,
	podExternalSensorConfigUpperWarningThreshold
		Unsigned32,
	podExternalSensorConfigAlarmResetThreshold
		Unsigned32,
	podExternalSensorConfigAlarmStateChangeDelay
		Unsigned32,
	podExternalSensorConfigEnabledThresholds
		BITS,
	podExternalSensorConfigAlarmState
		INTEGER
	}

podExternalSensorConfigIndex  OBJECT-TYPE
	SYNTAX 	INTEGER(0..255)
	MAX-ACCESS  	not-accessible
	STATUS 	current
	DESCRIPTION 
		"The index of the PDU External Sensor 
		configuration table entry"
	::= { podExternalSensorConfigEntry 1 }

podExternalSensorConfigLowerCriticalThreshold  OBJECT-TYPE
	SYNTAX 	Unsigned32
	MAX-ACCESS  	read-write
	STATUS 	current
	DESCRIPTION 
		"User-defined lower critical alarm threshold in podExternalSensorNamePlateUnits."
	::= { podExternalSensorConfigEntry 2 }

podExternalSensorConfigLowerWarningThreshold  OBJECT-TYPE
	SYNTAX 	Unsigned32
	MAX-ACCESS  	read-write
	STATUS 	current
	DESCRIPTION 
		"User-defined lower non-critical (warning) alarm threshold in podExternalSensorNamePlateUnits."
	::= { podExternalSensorConfigEntry 3 }

podExternalSensorConfigUpperCriticalThreshold  OBJECT-TYPE
	SYNTAX 	Unsigned32
	MAX-ACCESS  	read-write
	STATUS 	current
	DESCRIPTION 
		"User-defined upper critical alarm threshold in podExternalSensorNamePlateUnits."
	::= { podExternalSensorConfigEntry 4 }

podExternalSensorConfigUpperWarningThreshold  OBJECT-TYPE
	SYNTAX 	Unsigned32
	MAX-ACCESS  	read-write
	STATUS 	current
	DESCRIPTION 
		"User-defined upper non-critical (warning) alarm threshold in podExternalSensorNamePlateUnits."
	::= { podExternalSensorConfigEntry 5 }

podExternalSensorConfigAlarmResetThreshold  OBJECT-TYPE
	SYNTAX 	Unsigned32
	MAX-ACCESS  	read-write
	STATUS 	current
	DESCRIPTION 
		"The hysteresis used for deassertions."
	::= { podExternalSensorConfigEntry 6 }

podExternalSensorConfigAlarmStateChangeDelay  OBJECT-TYPE
	SYNTAX 	Unsigned32
	MAX-ACCESS  	read-write
	STATUS 	current
	DESCRIPTION 
		"The delay measured in samples before a state is 
		asserted. If the value is zero, then the state is 
		asserted as soon as it is detected; if it is non-zero, 
		say n, then the assertion condition must exist for n+1 
		consecutive samples before the corresponding assertion 
		event is reported."
	::= { podExternalSensorConfigEntry 7 }

podExternalSensorConfigEnabledThresholds  OBJECT-TYPE
	SYNTAX 	BITS {
		lowerCritical (0),
		lowerWarning (1),
		upperWarning (2),
		upperCritical (3),
		binarySensorAlarm (4)
	}
	MAX-ACCESS  	read-write
	STATUS 	current
	DESCRIPTION 
		"A bit string indicating which alarm 
		thresholds are enabled."
	::= { podExternalSensorConfigEntry 8 }

podExternalSensorConfigAlarmState OBJECT-TYPE
	SYNTAX 	INTEGER {
		on (1),
		off (0)
	}
	MAX-ACCESS  	read-write
	STATUS 	current
	DESCRIPTION 
		"User defined alarm state of external sensor"
	::= { podExternalSensorConfigEntry 9 }
	
podExternalSensorSTATUSTable  OBJECT-TYPE
	SYNTAX SEQUENCE OF PodExternalSensorSTATUSEntry
	MAX-ACCESS  	not-accessible
	STATUS 	current
	DESCRIPTION 
		"A table of PDU External Sensor STATUS data"
	::= { podExternalSensor 4 }
	
podExternalSensorSTATUSEntry  OBJECT-TYPE
	SYNTAX 	PodExternalSensorSTATUSEntry
	MAX-ACCESS  	not-accessible
	STATUS 	current
	DESCRIPTION 
		"STATUS data from the PDU External Sensor 
		being queried"
	INDEX { podUnitSTATUSIndex, podExternalSensorSTATUSIndex }
	::= { podExternalSensorSTATUSTable 1 }

PodExternalSensorSTATUSEntry ::= SEQUENCE {
	podExternalSensorSTATUSIndex
		Integer32,
	podExternalSensorSTATUSName
		DisplayString,
	podExternalSensorSTATUSAisle
		INTEGER,
	podExternalSensorSTATUSCommSTATUS
		INTEGER,
	podExternalSensorSTATUSState
		INTEGER,
	podExternalSensorSTATUSValue
		Integer32,
	podExternalSensorSTATUSTimeStamp
		DisplayString,
	podExternalSensorSTATUSHighPrecisionValue
		Integer32
	}

podExternalSensorSTATUSIndex  OBJECT-TYPE
	SYNTAX 	INTEGER(0..255)
	MAX-ACCESS  	not-accessible
	STATUS 	current
	DESCRIPTION 
		"The index of the PDU External Sensor STATUS table entry"
	::= { podExternalSensorSTATUSEntry 1 }

podExternalSensorSTATUSName  OBJECT-TYPE
	SYNTAX 	DisplayString
	MAX-ACCESS  	read-only
	STATUS 	current
	DESCRIPTION 
		"The user-defined name for the External Sensor"
	::= { podExternalSensorSTATUSEntry 2 }

podExternalSensorSTATUSAisle  OBJECT-TYPE
	SYNTAX 	INTEGER {
		hotAisle (1),
		coldAisle (2)
	}
	MAX-ACCESS  	read-write
	STATUS 	current
	DESCRIPTION 
		"Indicates whether the external sensor is 
		in a hot or cold aisle"
	::= { podExternalSensorSTATUSEntry 3 }

podExternalSensorSTATUSCommSTATUS  OBJECT-TYPE
	SYNTAX 	INTEGER {
		notInstalled (1),
		commsOk (2),
		commsLost (3)
	}
	MAX-ACCESS  	read-only
	STATUS 	current
	DESCRIPTION 
		"The communications STATUS of the sensor"
	::= { podExternalSensorSTATUSEntry 4 }

podExternalSensorSTATUSState  OBJECT-TYPE
	SYNTAX 	INTEGER {
		notPresent (0), alarmed (1), normal (2), belowLowerCritical (3), belowLowerWarning (4), aboveUpperWarning (5), aboveUpperCritical (6)
	}
	MAX-ACCESS  	read-only
	STATUS 	current
	DESCRIPTION 
		"This OID reports the current state of the sensor. 
			A notPresent (0) response indicates that no sensor is attached.
			An alarmed (1) response indicates that the sensor is present 
			and its measured reading indicates alarmed.
			A normal (2) response indicates that the sensor is present 
			and its measured reading lies within all thresholds.
			A belowLowerCritical (3) response indicates that the sensor 
			is present and its measured reading lies below the lower critical threshold.
			A belowLowerWarning (4) response indicates that the sensor 
			is present and its measured reading lies below the lower warning threshold.
			An aboveUpperWarning (5) response indicates that the sensor 
			is present and its measured reading lies above the upper warning threshold.
			An aboveUpperCritical (6) response indicates that the sensor 
			is present and its measured reading lies above the upper critical threshold."
	::= { podExternalSensorSTATUSEntry 5 }

podExternalSensorSTATUSValue  OBJECT-TYPE
	SYNTAX 	Integer32
	MAX-ACCESS  	read-only
	STATUS 	current
	DESCRIPTION 
		"Sensor reading in podExternalSensorConfigUnits value."
	::= { podExternalSensorSTATUSEntry 6 }

podExternalSensorSTATUSTimeStamp  OBJECT-TYPE
	SYNTAX 	DisplayString
	MAX-ACCESS  	read-only
	STATUS 	current
	DESCRIPTION 
		"The sensor reading timestamp."
	::= { podExternalSensorSTATUSEntry 7 }

podExternalSensorSTATUSHighPrecisionValue  OBJECT-TYPE
	SYNTAX 	Integer32
	MAX-ACCESS  	read-only
	STATUS 	current
	DESCRIPTION 
		"Temperature sensor reading in tenths of podExternalSensorConfigUnits value.
		This OID is applied to temperature sensor only"
	::= { podExternalSensorSTATUSEntry 8 }
	
-- Start podServerPing
podServerPingTableSize  OBJECT-TYPE
	SYNTAX 	INTEGER(0..255)
	MAX-ACCESS  	read-only
	STATUS 	current
	DESCRIPTION 
		"The total number of Servers"
	::= { podServerPing 1 }

podServerPingTable  OBJECT-TYPE
	SYNTAX SEQUENCE OF PodServerPingEntry
	MAX-ACCESS  	not-accessible
	STATUS 	current
	DESCRIPTION 
		"A table of Server Ping data"
	::= { podServerPing 2 }

podServerPingEntry  OBJECT-TYPE
	SYNTAX 	PodServerPingEntry
	MAX-ACCESS  	not-accessible
	STATUS 	current
	DESCRIPTION 
		"Server Ping data from the server being queried. 
		The number of entries equals the value of podServerPingTableSize."
	INDEX { podUnitConfigIndex, podServerPingIndex }
	::= { podServerPingTable 1 }

PodServerPingEntry ::= SEQUENCE {
	podServerPingIndex
		Integer32,
	podServerPingServerIPAddress
		DisplayString,
	podServerPingEnabled
		INTEGER
	}

podServerPingIndex  OBJECT-TYPE
	SYNTAX 	INTEGER(0..255)
	MAX-ACCESS  	not-accessible
	STATUS 	current
	DESCRIPTION 
		"The index of the PDU podServerPing table entry"
	::= { podServerPingEntry 1 }

podServerPingServerIPAddress  OBJECT-TYPE
	SYNTAX 	DisplayString
	MAX-ACCESS  	read-only
	STATUS 	current
	DESCRIPTION 
		"The IP Address/host name of the server "
	::= { podServerPingEntry 2 }

podServerPingEnabled  OBJECT-TYPE
	SYNTAX 	INTEGER {
		false (0), true (1)
	}
	MAX-ACCESS  	read-write
	STATUS 	current
	DESCRIPTION 
		"Is ping enabled for this server?"
	::= { podServerPingEntry 3 }

--  Smart Cabinet

podUnitSmartCabinetTableSize  OBJECT-TYPE
	SYNTAX 	INTEGER(0..255)
	MAX-ACCESS  	read-only
	STATUS 	current
	DESCRIPTION 
		"The total number of Smart Cabinet Configuration "
	::= { podSmartCabinet 1 }

podUnitSmartCabinetTable  OBJECT-TYPE
	SYNTAX SEQUENCE OF PodUnitSmartCabinetEntry
	MAX-ACCESS  	not-accessible
	STATUS 	current
	DESCRIPTION 
		"A table of Smart Cabinet"
	::= { podSmartCabinet 2 }

podUnitSmartCabinetEntry  OBJECT-TYPE
	SYNTAX 	PodUnitSmartCabinetEntry
	MAX-ACCESS  	not-accessible
	STATUS 	current
	DESCRIPTION 
		"Information of Smart Cabinet"
	INDEX { podUnitSmartCabinetHidIndex }
	::= { podUnitSmartCabinetTable 1 }

PodUnitSmartCabinetEntry ::= SEQUENCE {
  podUnitSmartCabinetHidIndex
  	Integer32,
	podUnitSmartCabinetHidSerial
		DisplayString,
	podUnitSmartCabinetHidAisle
		Integer32
	}
	
podUnitSmartCabinetHidIndex   OBJECT-TYPE
	SYNTAX 	INTEGER(1..256)
	MAX-ACCESS  	not-accessible
	STATUS 	current
	DESCRIPTION 
		"The index of the PDU Smart Cabinet table entry"
	::= { podUnitSmartCabinetEntry 1 }	
	
podUnitSmartCabinetHidSerial   OBJECT-TYPE
	SYNTAX 	DisplayString
	MAX-ACCESS  	read-only
	STATUS 	current
	DESCRIPTION 
		"The serial number of the PDU Smart Cabinet"
	::= { podUnitSmartCabinetEntry 2 }		
	
podUnitSmartCabinetHidAisle	OBJECT-TYPE
	SYNTAX 	INTEGER {
		hotAisle (1),
		coldAisle (2)
	}
	MAX-ACCESS  	read-only
	STATUS 	current
	DESCRIPTION 
		"Aisle of Smart Cabinet. "
	::= { podUnitSmartCabinetEntry 3 }
		
podUnitSmartCabinetControl  	OBJECT IDENTIFIER ::= { podSmartCabinet 3 }

podUnitSmartCabinetControlHidSerial     OBJECT-TYPE
  SYNTAX 	DisplayString
	MAX-ACCESS  	read-write
	STATUS 	current
	DESCRIPTION 
		"Hid Serial number"
	::= { podUnitSmartCabinetControl 1 }  
	
podUnitSmartCabinetControlCardIndex     OBJECT-TYPE
  SYNTAX 	Integer32
	MAX-ACCESS  	read-write
	STATUS 	current
	DESCRIPTION 
		"Card Index"
	::= { podUnitSmartCabinetControl 2 }  
		

podUnitSmartCabinetControlUserName  OBJECT-TYPE
	SYNTAX 	DisplayString
	MAX-ACCESS  	read-write
	STATUS 	current
	DESCRIPTION 
		"User name of ID card"
	::= { podUnitSmartCabinetControl 3 }

podUnitSmartCabinetControlCardID		OBJECT-TYPE
	SYNTAX 	Integer32
	MAX-ACCESS  	read-write
	STATUS 	current
	DESCRIPTION 
		"Card ID."
	::= { podUnitSmartCabinetControl 4 }

podUnitSmartCabinetControlTimestamp	OBJECT-TYPE
	SYNTAX 	DisplayString
	MAX-ACCESS  	read-write
	STATUS 	current
	DESCRIPTION 
		"Indicates the date and time of information update"
	::= { podUnitSmartCabinetControl 5 }
		
podUnitSmartCabinetCardIDEdit	OBJECT-TYPE
	SYNTAX 	INTEGER {
		grant (0), remove (1)
	}
	MAX-ACCESS  	read-write
	STATUS 	current
	DESCRIPTION 
		"Smart Cabinet edit CardID "
	::= { podUnitSmartCabinetControl 7 }
	
podUnitSmartCabinetLockStateTable  OBJECT-TYPE
	SYNTAX SEQUENCE OF PodUnitSmartCabinetLockStateEntry
	MAX-ACCESS  	not-accessible
	STATUS 	current
	DESCRIPTION 
		"A table of Smart Cabinet aisle state control"
	::= { podSmartCabinet 4 }

podUnitSmartCabinetLockStateEntry  OBJECT-TYPE
	SYNTAX 	PodUnitSmartCabinetLockStateEntry
	MAX-ACCESS  	not-accessible
	STATUS 	current
	DESCRIPTION 
		"Information of Smart Cabinet Lock State"
	INDEX { podUnitSmartCabinetLockStateIndex }
	::= { podUnitSmartCabinetLockStateTable 1 }

PodUnitSmartCabinetLockStateEntry ::= SEQUENCE {
  podUnitSmartCabinetLockStateIndex
  	Integer32,
	podUnitSmartCabinetColdAisleLockState
		Integer32,
	podUnitSmartCabinetHotAisleLockState
		Integer32,
	podUnitSmartCabinetColdAisleLockLabel
		DisplayString,
	podUnitSmartCabinetHotAisleLockLabel
		DisplayString
	}
	
podUnitSmartCabinetLockStateIndex   OBJECT-TYPE
	SYNTAX 	INTEGER(1..256)
	MAX-ACCESS  	not-accessible
	STATUS 	current
	DESCRIPTION 
		"The index of the PDU Smart Cabinet table entry"
	::= { podUnitSmartCabinetLockStateEntry 1 }	

podUnitSmartCabinetColdAisleLockState	OBJECT-TYPE
	SYNTAX 	INTEGER {
		unlock (0), lock (1), notPresent (2)
	}
	MAX-ACCESS  	read-write
	STATUS 	current
	DESCRIPTION 
		"Smart Cabinet ColdAisle lock state "
	::= { podUnitSmartCabinetLockStateEntry 2 }

podUnitSmartCabinetHotAisleLockState	OBJECT-TYPE
	SYNTAX 	INTEGER {
		unlock (0), lock (1), notPresent (2)
	}
	MAX-ACCESS  	read-write
	STATUS 	current
	DESCRIPTION 
		"Smart Cabinet HotAisle lock state "
	::= { podUnitSmartCabinetLockStateEntry 3 }		

podUnitSmartCabinetColdAisleLockLabel  OBJECT-TYPE
	SYNTAX 	DisplayString
	MAX-ACCESS  	read-only
	STATUS 	current
	DESCRIPTION 
		"Label of cold aisle smartcabinet"
	::= { podUnitSmartCabinetLockStateEntry 4 }
				
podUnitSmartCabinetHotAisleLockLabel  OBJECT-TYPE
	SYNTAX 	DisplayString
	MAX-ACCESS  	read-only
	STATUS 	current
	DESCRIPTION 
		"Label of hot aisle smartcabinet"
	::= { podUnitSmartCabinetLockStateEntry 5 }				
				
-- Traps Information
podtrapsInfo  OBJECT IDENTIFIER ::= { podTraps 1 }

podtrapsInfoTable  OBJECT-TYPE
	SYNTAX SEQUENCE OF PodtrapsInfoEntry
	MAX-ACCESS  	not-accessible
	STATUS 	current
	DESCRIPTION 
       "A list of Trap Information entries. The number of
            entries are given by the value of podUnitTableSize."	
	::= { podtrapsInfo 1 }
	
podtrapsInfoEntry  OBJECT-TYPE
	SYNTAX 	PodtrapsInfoEntry
	MAX-ACCESS  	not-accessible
	STATUS 	current
	DESCRIPTION 
		"An entry containing objects used in traps"
	INDEX { podtrapsInfoIndex }
	::= { podtrapsInfoTable 1 }

PodtrapsInfoEntry ::= SEQUENCE {
	podtrapsInfoIndex
		Integer32,
	poduserName
		DisplayString,
	poduserUpdated
		DisplayString,
	podfirmwareVersion
		DisplayString,
	podroleUpdated
		DisplayString,
	podsmtpRecipients
		DisplayString,
	podsmtpServer
		DisplayString
	}

podtrapsInfoIndex  OBJECT-TYPE
	SYNTAX 	INTEGER(1..256)
	MAX-ACCESS  	not-accessible
	STATUS 	current
	DESCRIPTION 
		"The index of the traps table entry"
	::= { podtrapsInfoEntry 1 }


poduserName  OBJECT-TYPE
	SYNTAX 	DisplayString
	MAX-ACCESS  	read-only
	STATUS 	current
	DESCRIPTION 
		"The user currently logged in."
	::= { podtrapsInfoEntry 2 }
	
poduserUpdated  OBJECT-TYPE
	SYNTAX 	DisplayString
	MAX-ACCESS  	read-only
	STATUS 	current
	DESCRIPTION 
		"The user added, deleted, or modified."
	::= { podtrapsInfoEntry 3 }

podfirmwareVersion  OBJECT-TYPE
	SYNTAX 	DisplayString
	MAX-ACCESS  	read-only
	STATUS 	current
	DESCRIPTION 
		"The version of Firmware."
	::= { podtrapsInfoEntry 4 }

podroleUpdated  OBJECT-TYPE
	SYNTAX 	DisplayString
	MAX-ACCESS  	read-only
	STATUS 	current
	DESCRIPTION 
		"The role added, deleted, or modified."
	::= { podtrapsInfoEntry 5 }

podsmtpRecipients  OBJECT-TYPE
	SYNTAX 	DisplayString
	MAX-ACCESS  	read-only
	STATUS 	current
	DESCRIPTION 
		"Comma separated list of SMTP  recipients"
	::= { podtrapsInfoEntry 6 }

podsmtpServer  OBJECT-TYPE
	SYNTAX 	DisplayString
	MAX-ACCESS  	read-only
	STATUS 	current
	DESCRIPTION 
		"The IP address/host name of the SMTP server"
	::= { podtrapsInfoEntry 7 }

podIndex  OBJECT-TYPE
	SYNTAX 	Integer32
	MAX-ACCESS  	accessible-for-notify
	STATUS 	current
	DESCRIPTION 
		"A unique value for PDU. Its value ranges between 1 
		and the value of PDU count"
	::= { podtrapsInfo 2 }

podexternalSensorIndex  OBJECT-TYPE
	SYNTAX 	Integer32
	MAX-ACCESS  	accessible-for-notify
	STATUS 	current
	DESCRIPTION 
		"A unique value for each sensor. Its value ranges between 1 
		and the value of external sensor count."
	::= { podtrapsInfo 3 }

podserverPing  OBJECT-TYPE
	SYNTAX 	INTEGER {
		pingEnable (1),
		pingDisable (2),
		serverReachable (3),
		serverNotReachable (4)
	}
	MAX-ACCESS  	accessible-for-notify
	STATUS 	current
	DESCRIPTION 
		"Whether server ping has been enabled or disabled and 
		whether the server is reachable or not reachable"
	::= { podtrapsInfo 4 }

podusbDevice  OBJECT-TYPE
	SYNTAX 	INTEGER {
		connected (1),
		disconnected (2)
	}
	MAX-ACCESS  	accessible-for-notify
	STATUS 	current
	DESCRIPTION 
		"Whether a USB device has been connected or disconnected"
	::= { podtrapsInfo 5 }

poderrorDescription  OBJECT-TYPE
	SYNTAX 	DisplayString
	MAX-ACCESS  	accessible-for-notify
	STATUS 	current
	DESCRIPTION 
		"Description of the Error"
	::= { podtrapsInfo 6 }

poddaisyChain  OBJECT-TYPE
	SYNTAX 	INTEGER {
		connected (1),
		disconnected (2)
	}
	MAX-ACCESS  	accessible-for-notify
	STATUS 	current
	DESCRIPTION 
		"Whether a daisy chain member has been connected or disconnected"
	::= { podtrapsInfo 7 }

podsystemCommunication  OBJECT-TYPE
	SYNTAX 	INTEGER {
		ok (1),
		lost (2)
	}
	MAX-ACCESS  	accessible-for-notify
	STATUS 	current
	DESCRIPTION 
		"Whether the Network management card has lost contact with daisy a chain member."
	::= { podtrapsInfo 8 }

podnetworkCardStart  		NOTIFICATION-TYPE
				OBJECTS {   podIndex,
						podNamePlateName,
			 		    podNamePlateInetAddressType,
					    podNamePlateIPAddress,
					    sysContact,
					    sysName,
					    sysLocation  }
				STATUS 	current
				DESCRIPTION 
					"The network card has started"
				::= { podTraps 2 }
	
podnetworkCardReset  		NOTIFICATION-TYPE
				OBJECTS {   podIndex,
						podNamePlateName,
			 		    poduserName,
					    podNamePlateInetAddressType,
					    podNamePlateIPAddress,
					    sysContact,
					    sysName,
					    sysLocation }
				STATUS 	current
				DESCRIPTION 
					"The network card was reset via the web or command line interface."
				::= { podTraps 3 }
	
poduserLogin  			NOTIFICATION-TYPE
				OBJECTS {   podIndex,
						podNamePlateName, 
    					poduserName, 
					    podNamePlateInetAddressType,
					    podNamePlateIPAddress,
					    sysContact,
					    sysName,
					    sysLocation }
				STATUS 	current
				DESCRIPTION 
					"A user logged in"
				::= { podTraps 4 }

poduserLogoff  			NOTIFICATION-TYPE
				OBJECTS {   podIndex,
							podNamePlateName, 
    					    poduserName, 
					    podNamePlateInetAddressType,
					    podNamePlateIPAddress,
					    sysContact,
					    sysName,
					    sysLocation }
				STATUS 	current
				DESCRIPTION 
					" A user logged off"
				::= { podTraps 5 }

poduserAuthenticationFailed  	NOTIFICATION-TYPE
				OBJECTS {   podIndex,
							podNamePlateName, 
    					    poduserName, 
					    podNamePlateInetAddressType,
					    podNamePlateIPAddress,
					    sysContact,
					    sysName,
					    sysLocation }
				STATUS 	current
				DESCRIPTION 
					"A user authentication attempt failed."
				::= { podTraps 6 }
	
poduserSessionTimeout  		NOTIFICATION-TYPE
				OBJECTS {   podIndex,
							podNamePlateName, 
    					    poduserName, 
					    podNamePlateInetAddressType,
					    podNamePlateIPAddress,
					    sysContact,
					    sysName,
					    sysLocation }
				STATUS 	current
				DESCRIPTION 
					"A user session timed out"
				::= { podTraps 7 }

poduserAdded  			NOTIFICATION-TYPE
				OBJECTS {   podIndex,
							podNamePlateName, 
    					    poduserName, 
    					    podNamePlateInetAddressType,
					    podNamePlateIPAddress,
    					    poduserUpdated,
    					    sysContact,
					    sysName,
					    sysLocation }
				STATUS 	current
				DESCRIPTION 
					"A user account was added to system."
				::= { podTraps 8 }
	
poduserModified  			NOTIFICATION-TYPE
				OBJECTS {   podIndex,
							podNamePlateName, 
    					    poduserName, 
    					    podNamePlateInetAddressType,
					    podNamePlateIPAddress,
    					    poduserUpdated,
    					    sysContact,
					    sysName,
					    sysLocation }
				STATUS 	current
				DESCRIPTION 
					"A user account was modified."
				::= { podTraps 9 }
	
poduserDeleted  			NOTIFICATION-TYPE
				OBJECTS {   podIndex,
							podNamePlateName, 
    					    poduserName, 
    					    podNamePlateInetAddressType,
					    podNamePlateIPAddress,
    					    poduserUpdated,
    					    sysContact,
					    sysName,
					    sysLocation }
				STATUS 	current
				DESCRIPTION 
					"A user account was deleted."
				::= { podTraps 10 }

podroleAdded  			NOTIFICATION-TYPE
				OBJECTS {   podIndex,
							podNamePlateName, 
    					    poduserName, 
					    podNamePlateInetAddressType,
					    podNamePlateIPAddress,
					    podroleUpdated,
    					    sysContact,
					    sysName,
					    sysLocation }
				STATUS 	current
				DESCRIPTION 
					"A user role was added."
				::= { podTraps 11 }
	
podroleModified  			NOTIFICATION-TYPE
				OBJECTS {   podIndex,
							podNamePlateName, 
    					    poduserName, 
					    podNamePlateInetAddressType,
					    podNamePlateIPAddress,
					    podroleUpdated,
    					    sysContact,
					    sysName,
					    sysLocation }
				STATUS 	current
				DESCRIPTION 
					"A user role was modified."
				::= { podTraps 12 }

podroleDeleted  			NOTIFICATION-TYPE
				OBJECTS {   podIndex,
							podNamePlateName, 
    					    poduserName, 
					    podNamePlateInetAddressType,
					    podNamePlateIPAddress,
					    podroleUpdated,
    					    sysContact,
					    sysName,
					    sysLocation }
				STATUS 	current
				DESCRIPTION 
					"A user role was deleted."
				::= { podTraps 13 }

podfirmwareUpdateStarted  	NOTIFICATION-TYPE
				OBJECTS {   podIndex,
							podNamePlateName, 
    					    poduserName, 
					    podNamePlateInetAddressType,
					    podNamePlateIPAddress,
					    podfirmwareVersion,
    					    sysContact,
					    sysName,
					    sysLocation }
				STATUS 	current
				DESCRIPTION 
					"A firmware update has started."
				::= { podTraps 14 }

podfirmwareUpdateCompleted  	NOTIFICATION-TYPE
				OBJECTS {   podIndex,
							podNamePlateName, 
    					    poduserName, 
					    podNamePlateInetAddressType,
					    podNamePlateIPAddress,
					    podfirmwareVersion,
    					    sysContact,
					    sysName,
					    sysLocation }
				STATUS 	current
				DESCRIPTION 
					"The firmware update has completed."
				::= { podTraps 15 }
	
poduserBlocked  			NOTIFICATION-TYPE
				OBJECTS {   podIndex,
							podNamePlateName, 
    					    poduserName, 
					    podNamePlateInetAddressType,
					    podNamePlateIPAddress,
					    sysContact,
					    sysName,
					    sysLocation }
				STATUS 	current
				DESCRIPTION 
					"A user is blocked."
				::= { podTraps 16 }
	
podoutletControl  			NOTIFICATION-TYPE
				OBJECTS {   podIndex,
							podNamePlateName, 
    	 				    poduserName, 
	  				    podNamePlateInetAddressType,
	  				    podNamePlateIPAddress,
	  				    podOutletSwitchedControlNumber,
	  				    podOutletSwitchedSTATUSState, 
	  				    podOutletSwitchedControlCommand,
	  				    sysContact,
	  				    sysName,
	  				    sysLocation }
				STATUS 	current
				DESCRIPTION 
					"Outlet control operation applied."
				::= { podTraps 17 }

poduserPasswordChange  		NOTIFICATION-TYPE
				OBJECTS {   podIndex,
							podNamePlateName, 
    					    poduserName, 
    				    	    podNamePlateInetAddressType,
					    podNamePlateIPAddress,
    					    poduserUpdated,
    					    sysContact,
					    sysName,
					    sysLocation }
				STATUS 	current
				DESCRIPTION 
					"A user password was changed. "
				::= { podTraps 18 }
	
podpasswordSettingsChange  	NOTIFICATION-TYPE
				OBJECTS {   podIndex,
							podNamePlateName, 
    					    poduserName, 
					    podNamePlateInetAddressType,
					    podNamePlateIPAddress,
					    sysContact,
					    sysName,
					    sysLocation }
				STATUS 	current
				DESCRIPTION 
					"One or more password policy settings were changed."
				::= { podTraps 19 }

podlogFileCleared  			NOTIFICATION-TYPE
				OBJECTS {   podIndex,
							podNamePlateName, 
    					    poduserName, 
					    podNamePlateInetAddressType,
					    podNamePlateIPAddress,
					    sysContact,
					    sysName,
					    sysLocation }
				STATUS 	current
				DESCRIPTION 
					"The log file has been cleared."
				::= { podTraps 21 }
	
podConfigurationFileImported  	NOTIFICATION-TYPE
				OBJECTS {   podIndex,
							podNamePlateName, 
    					    poduserName, 
					    podNamePlateInetAddressType,
					    podNamePlateIPAddress,
					    sysContact,
					    sysName,
					    sysLocation }
				STATUS 	current
				DESCRIPTION 
					"PDU configuration file was imported."
				::= { podTraps 22 }

podConfigurationFileExported  	NOTIFICATION-TYPE
				OBJECTS {   podIndex,
							podNamePlateName, 
    					    poduserName, 
					    podNamePlateInetAddressType,
					    podNamePlateIPAddress,
					    sysContact,
					    sysName,
					    sysLocation }
				STATUS 	current
				DESCRIPTION 
					"PDU configuration file was exported"
				::= { podTraps 23 }

podUnitActivePowerStateChange  NOTIFICATION-TYPE
				OBJECTS {   podIndex,
							podNamePlateName, 
    	  				    podNamePlateInetAddressType,
	  				    podNamePlateIPAddress,
	  				    podUnitSTATUSLoadState,
	  				    podUnitSTATUSActivePower,
	  				    sysContact,
	  				    sysName,
	  				    sysLocation }
				STATUS 	current
				DESCRIPTION 
					"PDU unit active power state changes."
				::= { podTraps 24 }
	
podInputphaseVoltageStateChange  	NOTIFICATION-TYPE
					OBJECTS {   podIndex,
								podNamePlateName, 
    	  					    podNamePlateInetAddressType,
	  					    podNamePlateIPAddress,
	  					    podInputPhaseSTATUSCount, 
	  					    podInputPhaseSTATUSVoltageState, 
	  					    podInputPhaseSTATUSVoltage,
	  					    sysContact,
	  					    sysName,
	  					    sysLocation }
					STATUS 	current
					DESCRIPTION 
						"PDU input phase voltage state changes."
				::= { podTraps 25 }
	
podInputphaseCurrentStateChange  	NOTIFICATION-TYPE
					OBJECTS {   podIndex,
								podNamePlateName, 
    	  					    podNamePlateInetAddressType,
	  					    podNamePlateIPAddress,
	  					    podInputPhaseSTATUSCount, 
	  					    podInputPhaseSTATUSCurrentState, 
	  					    podInputPhaseSTATUSCurrent,
	  					    sysContact,
	  					    sysName,
	  					    sysLocation }
					STATUS 	current
					DESCRIPTION 
						"PDU input phase Current state changes."
				::= { podTraps 26 }
	
podCircuitBreakerCurrentStateChange  NOTIFICATION-TYPE
					OBJECTS {   podIndex,
								podNamePlateName, 
    	  					    podNamePlateInetAddressType,
	  					    podNamePlateIPAddress,
	  					    podCircuitBreakerSTATUSIndex, 
	  					    podCircuitBreakerSTATUSLoadState, 
	  					    podCircuitBreakerSTATUSCurrent,
	  					    sysContact,
	  					    sysName,
	  					    sysLocation }
					STATUS 	current
					DESCRIPTION 
						"PDU Circuit Breaker Current state changes."
				::= { podTraps 27 }

podOutletActivePowerStateChange  	NOTIFICATION-TYPE
					OBJECTS {   podIndex,
								podNamePlateName, 
    	  					    podNamePlateInetAddressType,
	  					    podNamePlateIPAddress,
	  					    podOutletMeteredSTATUSIndex, 
	  					    podOutletMeteredSTATUSLoadState, 
	  					    podOutletMeteredSTATUSActivePower,
	  					    sysContact,
	  					    sysName,
	  					    sysLocation }
					STATUS 	current
					DESCRIPTION 
						"PDU Metered Outlet Active Power state changes."
				::= { podTraps 28 }

podExternalSensorStateChange  NOTIFICATION-TYPE
				OBJECTS {   podIndex,
							podNamePlateName, 
    	  				    podNamePlateInetAddressType,
	  				    podNamePlateIPAddress,
	  				    podExternalSensorSTATUSIndex, 
	  				    podExternalSensorSTATUSName, 
	  				    podExternalSensorNamePlateType, 
					    podExternalSensorSTATUSAisle, 
					    podExternalSensorNamePlateUnits, 
					    podExternalSensorSTATUSState, 
					    podExternalSensorSTATUSValue,
	  				    sysContact,
	  				    sysName,
	  				    sysLocation }
				STATUS 	current
				DESCRIPTION 
					"PDU External Sensor state changes."
				::= { podTraps 29 }

podsmtpTransmissionFailure  	NOTIFICATION-TYPE
				OBJECTS {   podIndex,
							podNamePlateName, 
    	  				    podNamePlateInetAddressType,
	  				    podNamePlateIPAddress,
	  				    podsmtpRecipients,
	  				    podsmtpServer,
	  				    sysContact,
	  				    sysName,
    					    sysLocation }
				STATUS 	current
				DESCRIPTION 
					"SMTP message transmission failed."
				::= { podTraps 30 }
	
podldapError  			NOTIFICATION-TYPE
				OBJECTS {   podIndex,
							podNamePlateName, 
    	  				    podNamePlateInetAddressType,
	  				    podNamePlateIPAddress,
	  				    errorDescription,
	  				    sysContact,
	  				    sysName,
	  				    sysLocation }
				STATUS 	current
				DESCRIPTION 
					"A LDAP error occurred"
				::= { podTraps 31 }
				
podfirmwareUpdateFailed  		NOTIFICATION-TYPE
				OBJECTS {   podIndex,
							podNamePlateName, 
    					    poduserName, 
					    podNamePlateInetAddressType,
					    podNamePlateIPAddress,
					    podfirmwareVersion,
    					    sysContact,
					    sysName,
					    sysLocation }
				STATUS 	current
				DESCRIPTION 
					"A firmware update has failed."
				::= { podTraps 32 }
	
podserverPingState 		NOTIFICATION-TYPE
				OBJECTS {   podIndex,
							podNamePlateName, 
    	  				    poduserName,
	  				    podNamePlateInetAddressType,
	  				    podNamePlateIPAddress,
	  				    podServerPingServerIPAddress,
	  				    podserverPing,
    					    sysContact,
	  				    sysName,
	  				    sysLocation }
				STATUS 	current
				DESCRIPTION 
					"The Ping feature has been enabled."
				::= { podTraps 33 }
	
podbootloaderState 		NOTIFICATION-TYPE
				OBJECTS {   podIndex,
							podNamePlateName, 
    	  				    podNamePlateInetAddressType,
	  				    podNamePlateIPAddress,
    					sysContact,
	  				    sysName,
	  				    sysLocation }
				STATUS 	current
				DESCRIPTION 
					"Enter into Bootloader mode"
				::= { podTraps 34 }

poddaisyChainState 		NOTIFICATION-TYPE
				OBJECTS {   podIndex,
							podNamePlateName, 
    	  				    podNamePlateInetAddressType,
	  				    podNamePlateIPAddress,
	  				    poddaisyChain,
    					sysContact,
	  				    sysName,
	  				    sysLocation }
				STATUS 	current
				DESCRIPTION 
					"A daisy chain member has been connected or disconnected."
				::= { podTraps 35 }
	
podsystemInternalCommunicationLost  	NOTIFICATION-TYPE
					OBJECTS {   podIndex,
								podNamePlateName, 
    	  				    	podNamePlateInetAddressType,
	  				    	    podNamePlateIPAddress,
	  				    	    systemCommunication,
    	    					    sysContact,
	  				    	    sysName,
	  				   	    sysLocation }
					STATUS 	current
					DESCRIPTION 
						"Network management card has lost contaction with internal boards."
				::= { podTraps 36 }


podsmartCabinetLockerUnlock			NOTIFICATION-TYPE
					OBJECTS {   podIndex,
							podNamePlateName, 
    	  				    	podNamePlateInetAddressType,
	  				    	    podNamePlateIPAddress,
	  				    	    podUnitSmartCabinetHidSerial,
	  				    	    podUnitSmartCabinetHidAisle,
						    podExternalSensorSTATUSValue,
    	    					    sysContact,
	  				    	    sysName,
	  				   	    sysLocation }
					STATUS 	current
					DESCRIPTION 
						"The Cabinet lock is unlocked."
				::= { podTraps 37 }

podsmartCabinetLockerLock			NOTIFICATION-TYPE
					OBJECTS {   podIndex,
							podNamePlateName, 
    	  				    	podNamePlateInetAddressType,
	  				    	    podNamePlateIPAddress,
	  				    	    podUnitSmartCabinetHidSerial,
						    podUnitSmartCabinetHidAisle,
						    podExternalSensorSTATUSValue,
    	    					    sysContact,
	  				    	    sysName,
	  				   	    sysLocation }
					STATUS 	current
					DESCRIPTION 
						"The Cabinet lock is locked"
				::= { podTraps 38 }

podsmartCabinetSwapCard		NOTIFICATION-TYPE
					OBJECTS {   podIndex,
							podNamePlateName, 
    	  				    	podNamePlateInetAddressType,
	  				    	    podNamePlateIPAddress,
	  				    	    podUnitSmartCabinetHidSerial,
						    podUnitSmartCabinetHidAisle,
						    podUnitSmartCabinetControlCardID,
						    podExternalSensorSTATUSValue,
    	    					    sysContact,
	  				    	    sysName,
	  				   	    sysLocation }
					STATUS 	current
					DESCRIPTION 
						"Card is swapped"
				::= { podTraps 39 }

podsmartCabinetLockerLockDoorOpen		NOTIFICATION-TYPE
					OBJECTS {   podIndex,
							podNamePlateName, 
    	  				    	podNamePlateInetAddressType,
	  				    	    podNamePlateIPAddress,
	  				    	    podUnitSmartCabinetHidSerial,
						    podUnitSmartCabinetHidAisle,
						    podExternalSensorSTATUSValue,
    	    					    sysContact,
	  				    	    sysName,
	  				   	    sysLocation }
					STATUS 	current
					DESCRIPTION 
						"Locker locked but door open"
				::= { podTraps 40 }
				
podsmartCabinetLockerUnlockDoorClose		NOTIFICATION-TYPE
					OBJECTS {   podIndex,
							podNamePlateName, 
    	  				    	podNamePlateInetAddressType,
	  				    	    podNamePlateIPAddress,
	  				    	    podUnitSmartCabinetHidSerial,
						    podUnitSmartCabinetHidAisle,
						    podExternalSensorSTATUSValue,
    	    					    sysContact,
	  				    	    sysName,
	  				   	    sysLocation }
					STATUS 	current
					DESCRIPTION 
						"Locker unlocked but door close"
				::= { podTraps 41 }				

podsmartCabinetLockerAutolock		NOTIFICATION-TYPE
					OBJECTS {   podIndex,
							podNamePlateName, 
    	  				    	podNamePlateInetAddressType,
	  				    	    podNamePlateIPAddress,
	  				    	    podUnitSmartCabinetHidSerial,
						    podUnitSmartCabinetHidAisle,
						    podExternalSensorSTATUSValue,
    	    					    sysContact,
	  				    	    sysName,
	  				   	    sysLocation }
					STATUS 	current
					DESCRIPTION 
						"The cabinet locker is locked automatically"
				::= { podTraps 42 }		
				
podsmartCabinetDoorOpen		NOTIFICATION-TYPE
					OBJECTS {   podIndex,
							podNamePlateName, 
    	  				    	podNamePlateInetAddressType,
	  				    	    podNamePlateIPAddress,
	  				    	    podUnitSmartCabinetHidSerial,
						    podUnitSmartCabinetHidAisle,
						    podExternalSensorSTATUSValue,
    	    					    sysContact,
	  				    	    sysName,
	  				   	    sysLocation }
					STATUS 	current
					DESCRIPTION 
						"The cabinet door is  open"
				::= { podTraps 43 }	
				
podsmartCabinetDoorLock		NOTIFICATION-TYPE
					OBJECTS {   podIndex,
							podNamePlateName, 
    	  				    	podNamePlateInetAddressType,
	  				    	    podNamePlateIPAddress,
	  				    	    podUnitSmartCabinetHidSerial,
						    podUnitSmartCabinetHidAisle,
						    podExternalSensorSTATUSValue,
    	    					    sysContact,
	  				    	    sysName,
	  				   	    sysLocation }
					STATUS 	current
					DESCRIPTION 
						"The cabinet  door is locked"
				::= { podTraps 44 }										

podsmartCabinetDoorUnlock		NOTIFICATION-TYPE
					OBJECTS {   podIndex,
							podNamePlateName, 
    	  				    	podNamePlateInetAddressType,
	  				    	    podNamePlateIPAddress,
	  				    	    podUnitSmartCabinetHidSerial,
						    podUnitSmartCabinetHidAisle,
						    podExternalSensorSTATUSValue,
    	    					    sysContact,
	  				    	    sysName,
	  				   	    sysLocation }
					STATUS 	current
					DESCRIPTION 
						"The cabinet door is unlocked"
				::= { podTraps 45 }			

podsmartCabinetAllDoorLock		NOTIFICATION-TYPE
					OBJECTS {   podIndex,
							podNamePlateName, 
    	  				    	podNamePlateInetAddressType,
	  				    	    podNamePlateIPAddress,
	  				    	    podUnitSmartCabinetHidSerial,
						    podUnitSmartCabinetHidAisle,
						    podExternalSensorSTATUSValue,
    	    					    sysContact,
	  				    	    sysName,
	  				   	    sysLocation }
					STATUS 	current
					DESCRIPTION 
						"All cabinet door is locked"
				::= { podTraps 46 }			

podsystemReboot	  		NOTIFICATION-TYPE
				OBJECTS {   podIndex,
						podNamePlateName,
			 		    podNamePlateInetAddressType,
					    podNamePlateIPAddress,
					    sysContact,
					    sysName,
					    sysLocation  }
				STATUS 	current
				DESCRIPTION 
					"System has rebooted"
				::= { podTraps 50 }



END
